module sm-mod {
    yang-version 1.1;
    namespace "urn:yanglint:sm-mod";
    prefix "sm-mod";

    revision 2017-01-26 {
      description
        "initial";
      reference
        "";
    }

    container not-compiled {
        leaf first {
            type string;
        }
        leaf second {
            type string;
        }
    }
}
