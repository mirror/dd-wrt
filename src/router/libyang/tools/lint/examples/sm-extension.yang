module sm-extension {
    yang-version 1.1;
    namespace "urn:sm-ext";
    prefix "sm-ext";

    import ietf-interfaces {
        prefix if;
    }
    import sm-mod {
        prefix sm-mod;
    }

    revision 2022-09-15 {
      description
        "initial";
      reference
        "";
    }

    list things {
        key "name";
        leaf name {
            type leafref {
              path "/if:interfaces/if:interface/if:name";
            }
        }
        leaf attribute {
            type uint32;
        }
    }

    augment "/if:interfaces/if:interface" {
        leaf thing-attribute {
            type leafref {
              path "/things/attribute";
            }
        }
    }
}
