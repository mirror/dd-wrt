submodule imp_aug_m1-s1 {
  belongs-to imp_aug_m1 {
    prefix m1;
  }

  import imp_aug_m2 {
    prefix m2;
  }

  grouping grp1 {
    uses m2:grp1  {
      augment "choice1" {
        case case3 {
          leaf c3_leaf {
            type empty;
          }
        }
      }
    }
  }
}
