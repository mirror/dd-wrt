module imp_aug_m2 {

  namespace "urn:fri:params:xml:ns:yang:imp_aug_m2";
  prefix m2;

  grouping grp1 {
    choice choice1 {
      case case1 {
        leaf c1_leaf {
          type uint32;
        }
      }
      case case2 {
        leaf c2_leaf {
          type string; 
        }
      }
    }
  }
}
