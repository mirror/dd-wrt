submodule submod1 {
    belongs-to "main_mod" {
      prefix m;
    }

    include submod_r {
      revision-date "2016-06-20";
    }

    revision "2016-06-20" {
      description "Initial revision.";
    }

    leaf submod1 {
        type int32;
    }
}
