module mod_r {
    namespace "urn:cesnet:test:r";
    prefix "r";

    revision "2016-06-20" {
      description "Second revision.";
    }

    revision "2016-06-19" {
      description "Initial revision.";
    }

    grouping grp {
        leaf b {type uint32;}
    }
}
