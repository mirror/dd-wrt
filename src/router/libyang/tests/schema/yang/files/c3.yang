module c3 {
  namespace "urn:c3";
  prefix c3_mod;

  import c1 {
    prefix c1_mod;
  }
  import c2 {
    prefix c2_mod;
  }

  augment "/c1_mod:top/c2_mod:cont" {
    leaf leaf3 {
      type empty;
    }
  }
}
