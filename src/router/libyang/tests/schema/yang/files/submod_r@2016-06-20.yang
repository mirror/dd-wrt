submodule submod_r {
    belongs-to "main_mod" {
      prefix m;
    }

    revision "2016-06-20" {
      description "Second revision.";
    }

    revision "2016-06-19" {
      description "Initial revision.";
    }

    leaf submod_r {
        type string;
    }
}
