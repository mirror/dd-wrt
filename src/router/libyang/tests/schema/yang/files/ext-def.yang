module ext-def {
  yang-version 1.1;
  namespace "urn:ext-def";
  prefix e;

  revision 2017-01-18;

  extension a;

  extension b {
    argument x;
  }

  extension c {
    argument y {
      yin-element true;
    }
  }

  extension complex;

  extension complex-arrays;

  extension complex-mand;

  typedef mystring {
    type string;
  }

  leaf l1 {
    type string;
  }
  leaf l2 {
    e:a;
    e:b "one";
    e:b "two";
    type string;
    mandatory true {
      e:b "one";
      e:c "one";
    }
  }
  leaf-list ll1 {
    type uint8;
  }
  list lst1 {
    e:b "ten";
    key "id";
    leaf id {
      type string;
    }
    leaf val1 {
      type uint8;
    }
    leaf val2 {
      e:a;
      type uint8;
      units "meter" {
        e:a;
      }
      default "1";
    }
  }
  list lst2 {
    e:a;
    e:a;
    e:b "one";
    e:b "two";
    key "id";
    unique "val1" {
      e:a;
    }
    leaf id {
      type string;
    }
    leaf val1 {
      type uint8;
    }
    leaf val2 {
      type uint8;
    }
  }
}
