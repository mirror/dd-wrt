module z {

  namespace "urn:z";
  prefix "z";

  list list1 {
    key id;

    leaf id {
      type string;
    }

    list list2 {
      key id;

      leaf id {
        type string;
      }
    }
  }
}
