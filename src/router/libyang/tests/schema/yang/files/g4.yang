module g4 {
    namespace "urn:g4";
    prefix g4;

    import g2 {
        prefix g2;
    }
    import g3 {
        prefix g3;
    }

    augment "/g2:top/g3:cont1" {
        uses g3:group1 {
            when "g3:l1 = 'ahoj'";
        }
    }
}
