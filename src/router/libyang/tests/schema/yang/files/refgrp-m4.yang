module refgrp-m4 {

  namespace "urn:fri:params:xml:ns:yang:refgrp-m4";
  prefix rg-m4;

  grouping grp1 {
    choice choice1 {
      case case1 {
      }
      case case2 {
        anyxml xml1 {
        }
      }
    }
  }
}
