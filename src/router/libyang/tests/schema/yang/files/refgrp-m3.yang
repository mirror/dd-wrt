module refgrp-m3 {

  namespace "urn:fri:params:xml:ns:yang:refgrp-m3";
  prefix rg-m3;

  import refgrp-m4 {
    prefix rg-m4;
  }

  import refgrp-m2 {
    prefix rg-m2;
  }

  notification ntf1 {
    uses rg-m4:grp1 {
      augment "choice1/case1" {
        uses rg-m2:grp1;
        leaf aleaf1 {
          type string;
        }
      }
    }
  }
}
