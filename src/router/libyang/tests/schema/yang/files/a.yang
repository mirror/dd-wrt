module a {
  namespace "urn:a";
  prefix a_mod;

  include asub;
  include atop;

  feature foo;

  grouping gg {
    leaf bar-gggg {
      type string;
    }
  }

  container x {
    leaf bar-leaf {
      if-feature bar;
      type string;
    }
    uses gg {
      if-feature bar;
    }
    leaf baz {
      if-feature foo;
      type string;
    }
    leaf bubba {
      type string;
    }
  }
  augment "/x" {
    if-feature bar;
    container bar-y;
  }
  rpc bar-rpc {
    if-feature bar;
  }
  rpc foo-rpc {
    if-feature foo;
  }
}
