module b2 {
  namespace "urn:b2";
  prefix b2_mod;

  import b1 {
    prefix b1_mod;
  }

  augment "/b1_mod:top" {
    leaf leaf2 {
      type empty;
    }
    leaf leaf3 {
      type leafref {
        path "../b1_mod:leaf";
      }
    }
    leaf leaf4 {
      type leafref {
        path "../leaf2";
      }
    }
    leaf leaf5 {
      type leafref {
        path "../b2_mod:leaf2";
      }
    }
  }
}
