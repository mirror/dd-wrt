submodule asub {
  belongs-to a {
    prefix a_pref;
  }

  include atop;

  feature fox;

  notification bar-notif {
    if-feature bar;
  }
  notification fox-notif {
    if-feature fox;
  }
  augment "/a_pref:top" {
    if-feature bar;
    container bar-sub;
  }
  augment "/top" {
    container bar-sub2;
  }
}
