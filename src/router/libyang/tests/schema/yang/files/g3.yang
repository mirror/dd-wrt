module g3 {
    namespace "urn:g3";
    prefix g3;

    import g2 {
        prefix g2;
    }

    grouping group1 {
        container cont2 {
            leaf l2 {
                type string;
            }
        }

        leaf l3 {
            type leafref {
                path "/g2:top/g3:cont1/g3:l1";
            }
        }

        leaf l4 {
            must "/g2:top/g3:cont1/g3:l1 = 'bb'";
            type leafref {
                path "../cont2/l2";
            }
        }
    }

    augment "/g2:top" {
        container cont1 {
            must "../cont1/l1 != 'aa'";
            leaf l1 {
                type string;
            }
        }
    }
}
