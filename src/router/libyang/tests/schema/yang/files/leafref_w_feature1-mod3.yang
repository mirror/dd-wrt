module leafref_w_feature1-mod3 {

  namespace "urn:fri:params:xml:ns:yang:leafref_w_feature1-mod3";
  prefix lr-w-ftr1-m3;

  import leafref_w_feature1-mod1 {
    prefix lr-w-ftr1-m1;
  }
  import leafref_w_feature1-mod2 {
    prefix lr-w-ftr1-m2;
  }

  augment "/lr-w-ftr1-m1:cont1" {

    description "mod3's cont1 augment";

    container cont3 {
      list list3 {
        key name;
        leaf name {
          type string;
        }
        choice choice3 {
          case case3 {
            leaf-list llist3 {
              type lr-w-ftr1-m2:list2-ref;
            }
          }
        }
      }
    }
  }
}
