module z-dev {

    namespace "urn:z-dev";
    prefix z-dev;

    import z {
      prefix z;
    }

    import z-aug {
        prefix z-aug;
    }

    deviation /z:list1/z:list2/z-aug:leaf1 {
        deviate not-supported;
    }
}
