module leafref_w_feature2-mod1 {

  namespace "urn:fri:params:xml:ns:yang:leafref_w_feature2-mod1";
  prefix lr-w-ftr2-m1;

  feature feature2;

  container cont1 {
    if-feature feature2;
  }

  augment "/cont1" {

    container cont11 {

      list list11 {
        key name;

        leaf name {
          type string;
        }
      }
    }
  }

  augment "/cont1" {

    container cont12 {

      list list12 {
        key name;

        leaf name {
          type string;
        }

        leaf-list llist12 {
          type leafref {
            path "/cont1/cont11/list11/name";
          }
        }
      }
    }
  }
}
