submodule tree2_sub {
    belongs-to tree2 {
        prefix t2;
    }
    choice ch2 {
        case ca {
            container presence {
                presence "enable";
            }
        }
        leaf leaf2 {
            type string;
        } 
        default ca;
   }
}
