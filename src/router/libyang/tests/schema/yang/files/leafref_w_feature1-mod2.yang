module leafref_w_feature1-mod2 {

  namespace "urn:fri:params:xml:ns:yang:leafref_w_feature1-mod2";
  prefix lr-w-ftr1-m2;

  import leafref_w_feature1-mod1 {
    prefix lr-w-ftr1-m1;
  }

  typedef list2-ref {
    type leafref {
      path "/lr-w-ftr1-m1:cont1"
         + "/lr-w-ftr1-m2:cont2"
         + "/lr-w-ftr1-m2:list2"
         + "/lr-w-ftr1-m2:name";
    }
  }

  augment "/lr-w-ftr1-m1:cont1" {

    description "mod2's cont1 augment";

    container cont2 {
      list list2 {
        key name;
        leaf name {
          type string;
        }
      }
    }
  }
}
