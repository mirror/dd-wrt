module patterns {
  namespace urn:libyang:tests:patterns;
  prefix p;

  grouping a {
    typedef testtype {
      type string {
        pattern "[a-z]*";
      }
    }
    leaf a {
      type testtype;
    }
  }

  typedef toptype {
    type string {
      pattern "[A-Z]*";
    }
  }

  leaf c {
    type toptype;
  }
  uses a;
  uses b;

  grouping b {
    leaf b {
      type string {
        pattern "[0-9]*";
      }
    }
  }
}
