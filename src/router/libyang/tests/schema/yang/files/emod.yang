module emod {
  yang-version 1.1;
  namespace "urn:emod";
  prefix emod_pref;

  include esub1;
  include esub2;

  augment "/cont" {
    leaf leaf {
      type uint64;
    }
  }
  augment "/emod_pref:cont" {
    leaf leaf2 {
      type uint8;
    }
  }
  container cont;
}
