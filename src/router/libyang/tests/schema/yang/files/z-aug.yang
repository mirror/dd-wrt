module z-aug {

  namespace "urn:z-aug";
  prefix "z-aug";

  import z {
    prefix z;
  }

  augment "/z:list1/z:list2" {

    leaf leaf1 {
      type boolean;
    }

    leaf leaf2 {
      type string;
    }
  }
}
