module tree2 {
    namespace "urn:tree2";
    prefix t2;
   
    include tree2_sub;
    import tree1 {
        prefix t1;
    }
    
    leaf leaf1 {
        type string;
        default "test tree";
    } 

    leaf-list ll {
        type t1:type1;
    }
   
    augment /t1:cont {
        list list1 {
            key key1;
            leaf key1 {
                type leafref {
                    path "/t1:cont/list1/leaf2";
                }
            }
            leaf key2 {
                type leafref {
                    path "/t2:leaf2";
                }
            }
            uses t1:group1;
        }
    }
   
    augment /t2:ch2 {
        case cb {
            container presence1 {
                presence "enable";
            }
        }
    }
}
