module c {
       yang-version 1.1;
       namespace "urn:example:c";
       prefix "c";

       revision 2015-03-03;
       revision 2015-01-01;

       typedef bar {
         type string;
       }
     }
