module a {
       yang-version 1.1;
       namespace "urn:example:a";
       prefix "a";

       import b {
         prefix b;
         revision-date 2015-01-01;
       }
       import c {
         prefix c;
       }

       revision 2015-01-01;

       feature foo;

       augment "/b:x" {
         if-feature foo;

         leaf y {
           type b:myenum;
         }
       }

       container a {
         leaf x {
           type c:bar;
         }
       }
     }
