module d2 {
  namespace "urn:d2";
  prefix d2_mod;

  import d1 {
    prefix d1_pref;
  }

  feature d2_feat {
    if-feature "d1_pref:d1_feat";
  }

  identity d2_ident {
    base d1_pref:d1_ident;
  }

  typedef d2_type {
    type d1_pref:d1_type;
  }

  leaf d2_leaf {
    type leafref {
      path "/d1_pref:d1_leaf";
    }
  }

  leaf d2_leaf2 {
    type identityref {
      base d1_pref:d1_ident;
    }
    must "/d1_pref:d1_leaf < 6";
  }

  uses d1_pref:d1_group {
    when "/d1_pref:d1_leaf = 5";
  }
}
