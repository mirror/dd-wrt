module lists {
    namespace "urn:libyang:test:lists";
    prefix l;

    container cont {
        list list1 {
            key "key1";
            leaf key1 {
                type string;
            }

            leaf leaf1 {
                type uint32;
            }
        }

        leaf-list llist1 {
            type string;
        }
    }
}
