module xpath {
    namespace "urn:libyang:test:xpath";
    prefix x;

    container cont1 {
        list list1 {
            key "key1";
            leaf key1 {
                type string;
            }

            must "count(../list2[key2 = current()/key1]) = 1";
        }

        list list2 {
            key "key2";
            leaf key2 {
                type string;
            }

            must "starts-with(./key2, 'a') or (contains(substring(./key2, 2, 3), 'a') and not(starts-with(./key2, 'a')))";
        }
    }
}
