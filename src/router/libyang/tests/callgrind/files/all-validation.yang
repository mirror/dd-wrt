module all-validation {
    namespace "urn:libyang:test:all-validation";
    prefix av;
    yang-version 1.1;

    container cont1 {
        leaf leaf1 {
            type string {
                length "2..10|15";
            }
            default "def1";
        }

        leaf-list llist1 {
            type decimal64 {
                fraction-digits 5;
            }
            min-elements 2;
        }

        leaf-list llist2 {
            type uint16;
            max-elements 3;
        }

        leaf-list llist3 {
            type uint32;
            min-elements 3;
            max-elements 5;
        }

        list list1 {
            key "key1";
            unique "uniq1 cont2/uniq2 cont2/uniq3";
            leaf key1 {
                type string;
            }

            leaf uniq1 {
                type string;
                default "def2";
            }

            container cont2 {
                leaf uniq2 {
                    type bits {
                        bit bit1;
                        bit bit2;
                        bit bit3;
                        bit bit4;
                        bit bit5;
                    }
                }

                leaf uniq3 {
                    type int32;
                }
            }
        }

        choice choic1 {
            case cas1 {
                choice choic2 {
                    case cas2 {
                        leaf leaf3 {
                            type int64;
                        }
                    }

                    list list2 {
                        key "key2";
                        leaf key2 {
                            type string;
                        }

                        leaf-list llist4 {
                            type enumeration {
                                enum enum1;
                                enum enum2;
                                enum enum3;
                                enum enum4;
                                enum enum5;
                            }
                        }
                    }
                }
            }

            container dummy;
        }

        container cont3 {
            leaf leaf2 {
                type int32 {
                    range "-25..50|100..200";
                }
            }
        }

        leaf-list llist5 {
            type leafref {
                path /cont1/llist1;
            }
        }

        leaf-list llist6 {
            type instance-identifier;
        }

        typedef unum-type1 {
            type uint8;
        }

        typedef num-type1 {
            type int8;
        }

        typedef union-type {
            type union {
                type uint32;
                type decimal64 {
                    fraction-digits 7;
                }
            }
        }

        leaf-list llist7 {
            type union {
                type union {
                    type unum-type1;
                    type leafref {
                        path /cont1/llist5;
                    }
                }
                type num-type1;
                type union-type;
                type int64;
                type string;
            }
        }
    }
}
