module perf {
    yang-version 1.1;
    namespace "urn:sysrepo:tests:perf";
    prefix p;

    container cont {
        list lst {
            key "k1 k2";

            leaf k1 {
                type uint32;
            }

            leaf k2 {
                type string;
            }

            leaf l {
                type string;
            }

            leaf-list lfl {
                type uint32;
            }
        }
    }
}
