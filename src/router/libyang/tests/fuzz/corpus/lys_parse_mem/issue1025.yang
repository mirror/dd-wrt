module a {
	yang-version 1.1;
  	namespace "urn:all";
  	prefix all_mod;

  	grouping group1 {
    	leaf leaf1 {
       		type int64 {
        		range "1000 .. 50000" {
          			error:message
            		"Spec";
        		}
      		}
    	}
    }
}
