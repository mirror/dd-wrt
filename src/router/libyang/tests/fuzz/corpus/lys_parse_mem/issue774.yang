module state-lists {
    yang-version 1.1;
    namespace "urn:state-lists";
    prefix sl;

    container cont {
		config false;
		grouping group1 {
            leaf leaf3 {
     			type tdef2 {
      				length "3..9 | 30..40";
      				pattern "[ac
				}*";
    		}

    		units "none";
    		default "aaa";
  		}

		typedef tdef2 {
			type string {
				length "2..17 | 20..50";
				pattern "[ab]*";
			}
		}

  		container cont1 {
    		uses group1 {
      			if-feature "feat2";
      			refine "leaf1" {
        			if-feature "feat3";
				    must "24 - 4 = number('20')";
        			default "25";
        			config true;
        			mandatory false;
        			description "dsc";
        			reference "none";
      			}
    		}

			leaf leaf4 {
				type int64 {
					range "1000 .. 50000" {
						error-message
						"Special e        
					}
					.";
				}
			}
    	}

      }
    }
  }
}
