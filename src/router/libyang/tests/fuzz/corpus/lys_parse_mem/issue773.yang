module n00 {
	yang-version 1.1;
  	namespace "urn:all";
  	prefix all_mod;

  	container cont1 {
    	uses group1 {
    	}
  	}

  	grouping group1 {
    	leaf leaf1 {
       		type int64 {
        		range "1000 .. 50000" {
          			error-meeeeeeeeeeeeeeeeeeeeeeeeeeeeeeeeeeeeeeeeeeeeeeeeeeeeeeeeeeeeeeeeeeeeeeeeeeeeeeeeeeeeeaeeeeeeeeeeeeeeeee:eeeeeeeeeeeeeeeeeeeeeeeressage
            		"Spec";
        		}
      		}
    	}
    }
}è  leaf-list llist1 {
