module leaf0000 {
  namespace "0000000000000000000000000";
    prefix lr;

    container cont {
        leaf trg-bits {
            type bits {
				bit bit0;
				bit €;
				bit bit3;
    		}
        }
    }
}
