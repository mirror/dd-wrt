module links {
  yang-version 1.1;
  namespace "urn:mo:1";
  prefix yang;

  import ietf-yang-metadata {
    prefix md;
    revision-date 2016-08-05;
  }

  md:annotation value {
    reference "RFC7950 section 7.7.9.";
    description;
  }
}
