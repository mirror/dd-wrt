module links {
    yang-version 1.1;
    namespace "urn:module2";
    prefix mod2;
    leaf just-leaf {
        type in888888888888L888888888888888888888888888888888888888Rfalse;
        if-feature X77afalse;
        if-feature X77alse;
        if-feature LLLLLLLLLLLLLLLLLDDDDDDFDDDDDDDDDDDDDDDLLLLLLLLLTLLLLLLLLLLLLLLLLLLLLLLL|LLLLLLLLLLXLLL8888883888888888888888888a8888888888888888888L888888888888888888LLLLLLLLLLLLLLLLLLLLLLLLLLLLLLLLLL8888883888888888888888888a8888888888888888888L888888888888888888888888888888888888888Rfalse;
        if-feature X77afalse;
        if-feature X77alse;
        if-feature LLLLLLLLLLLLLLDDDDDDDDDDD888888888888888888888Rfalse;
        if-feature X77afalse;
        if-feature H77alse;
        if-feature LLLLLLLLLLLLLLDDDDDDDDDDDDDDDDDDDDDDDDDDDDDDDDDDDDDDDDDDDDDDDDDDDDDDDDDDDDDDDDDDDDDDDDDDDDDDDDDDDDD(DL,LLL888888388888888888888888888888888888888888888L888888888888888888888888888888888888888R888888R888888R88889888888888888888888888888?8888ean;
    }
}
