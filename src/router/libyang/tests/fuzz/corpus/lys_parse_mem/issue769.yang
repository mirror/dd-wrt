module mod6 {

    prefix abc;
    namespace "http://www.example.c;
    yang-version 1.1;

    container cont1 {
        //x" {
              
        }

        augment "/aug-cont" {
            list list2 {
                key "key2";
                leaf key2 {
                    type string;
                }
            }
            notification nn {
                typedef Mt {
                    type string {
                        length "1..255";
                    }
                }

                container log {
                    grouping g {
                        notification nn {
                            type j2an;
                        }
                    }
