module augment0 {
  yang-version 1.1;
  namespace "urn:test-augment0";
  prefix au0;

  import augment-target {
    prefix aug;
  }

  augment "/aug:cont" {
    leaf augmented-leaf {
      type string;
    }
  }
}
