module union {

  namespace "urn:uni";
  prefix uni;
  yang-version 1.1;

  identity base-identity {
  }

  identity identity-for-ref {
    base base-identity;
  }
  container union-test {
    list uniception {
      key union;
      leaf union {
        type union {
          type bits {
            bit CF {
              position 0;
            }
          }
          type boolean;
          type empty;
          type enumeration {
            enum zero;
            enum one;
          }
          type union {
            type identityref {
              base base-identity;
            }
            type uint8;
            type int8;
            type uint16;
            type int16;
            type uint32;
            type int32;
            type union {
              type uint64;
              type int64;
              type decimal64 {
                fraction-digits 2;
              }
            }
          }
        }
      }
    }
  }
}
