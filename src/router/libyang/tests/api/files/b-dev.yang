module b-dev {
  namespace "urn:b-dev";
  prefix b_dev_mod;

  import b {
    prefix b_mod;
    revision-date 2016-03-01;
  }

  deviation /b_mod:x/b_mod:bar-leaf {
    deviate add {
      config true;
    }
  }
}
