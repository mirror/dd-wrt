submodule bsub {
  belongs-to b {
    prefix b_pref;
  }

  include btop;

  feature fox;

  notification bar-notif {
    if-feature bar;
  }
  notification fox-notif {
    if-feature fox;
  }
  augment "/b_pref:top" {
    if-feature bar;
    container bar-sub;
  }
  augment "/top" {
    container bar-sub2;
  }
}
