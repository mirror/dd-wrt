module b {
  namespace "urn:b";
  prefix b_mod;

  revision 2015-01-01 {
    description
      "version 1";
    reference "RFC XXXX";
  }

  feature foo;

  grouping gg {
    leaf bar-gggg {
      type string;
    }
  }

  container x {
    leaf bar-leaf {
      type string;
    }
    uses gg;
    leaf baz {
      if-feature foo;
      type string;
    }
    leaf bubba {
      type string;
    }
  }
  rpc foo-rpc {
    if-feature foo;
  }
}
