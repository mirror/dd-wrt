module xpath-1.1 {
    namespace "urn:xpath-1.1";
    prefix xp;

    revision 2016-08-26 {
        description
        "initial revision";
    }

    identity ident1;

    identity ident2 {
        base ident1;
    }

    container top {
        leaf str1 {
            type string;
        }
        leaf str2 {
            type string;
        }
        leaf lref {
            type leafref {
                path /top/str1;
            }
        }
        leaf instid {
            type instance-identifier;
        }
        leaf identref {
            type identityref {
                base ident1;
            }
        }
        leaf enum {
            type enumeration {
                enum zero;
                enum one;
                enum two;
                enum ten {
                    value 10;
                }
            }
        }
        leaf bits {
            type bits {
                bit flag1;
                bit flag2;
                bit flag3;
            }
        }
    }
}
