module merge-dflt {
  namespace "urn:merge-dflt";
  prefix md;

  container top {
    leaf a {
      type string;
    }
    leaf b {
      type string;
    }
    leaf c {
      type string;
      default "c_dflt";
    }
  }
}
