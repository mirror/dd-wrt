module moddatanodes {
  yang-version 1.1;
  namespace "urn:yanglint:moddatanodes";
  prefix mdn;

  container dnc {
    leaf lf {
      type string;
    }
    leaf-list lfl {
      type string;
    }
    leaf mis {
      type string;
    }
    container con {
      list lt {
        key "kalf kblf";
        leaf kalf {
          type string;
        }
        leaf kblf {
          type string;
        }
        leaf vlf {
          type string;
        }
      }
    }
  }
}
