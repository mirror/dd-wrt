module modextleafref {
  namespace "urn:yanglint:modextleafref";
  prefix mel;

  list ls {
    key k;
    leaf k {
      type string;
    }
    leaf lf {
      type uint8;
    }
  }
  leaf lfr {
    type leafref {
      path "../ls/k";
    }
  }
  leaf lfrderef {
    type leafref {
      path "deref(../lfr)/../lf";
    }
  }
}
