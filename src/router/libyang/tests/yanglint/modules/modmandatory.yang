module modmandatory {
  namespace "urn:yanglint:modmandatory";
  prefix mm;

  container mmc {
    leaf lft {
      type int16;
      mandatory true;
    }
    leaf lff {
      type int16;
    }
  }
}
