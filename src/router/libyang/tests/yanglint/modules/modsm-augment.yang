module modsm-augment {
  yang-version 1.1;
  namespace "urn:yanglint:modsm-augment";
  prefix "msa";

  import modsm {
    prefix msm;
  }

  augment "/msm:root" {
    leaf alf {
      type string;
    }
  }
}
