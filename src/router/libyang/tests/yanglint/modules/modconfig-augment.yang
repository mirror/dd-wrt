module modconfig-augment {
  yang-version 1.1;
  namespace "urn:yanglint:modconfig-augment";
  prefix "mca";

  import modconfig {
    prefix mc;
  }

  augment "/mc:mcc" {
    leaf alf {
      type string;
    }
  }
}
