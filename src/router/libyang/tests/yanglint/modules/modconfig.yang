module modconfig {
  namespace "urn:yanglint:modconfig";
  prefix mc;

  container mcc {
    leaf lft {
      type string;
      config true;
      mandatory true;
    }
    leaf lff {
      type string;
      config false;
      mandatory true;
    }
  }
}
