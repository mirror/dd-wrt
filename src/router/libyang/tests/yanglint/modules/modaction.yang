module modaction {
  yang-version 1.1;
  namespace "urn:yanglint:modaction";
  prefix ma;

  container con {
    list ls {
      key "lfkey";
      leaf lfkey {
        type string;
      }
      action act {
        input {
          leaf lfi {
            type string;
          }
        }
        output {
          leaf lfo {
            type int16;
          }
        }
      }
    }
  }
}
