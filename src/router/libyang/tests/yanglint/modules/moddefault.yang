module moddefault {
  namespace "urn:yanglint:moddefault";
  prefix md;

  container mdc {
    leaf lf {
      type uint16;
    }
    leaf di {
      type int16;
      default "5";
    }
    leaf ds {
      type string;
      default "str";
    }
  }

}
