module modrpc {
  namespace "urn:yanglint:modrpc";
  prefix mr;

  rpc rpc {
    input {
      leaf lfi {
        type string;
      }
    }
    output {
      container con {
        leaf lfo {
          type int16;
        }
      }
    }
  }
}
