module mod4 {

    prefix abc;
    namespace "urn:cesnet:mod4";

    container ccc {
        list ll {
            key "k";

            leaf k { type string; }

            config "true";

            reference "test reference";

            description "test description";

            key l; // duplicated

            leaf l { type boolean; }
        }
    }
}
