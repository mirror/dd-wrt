module mod3 {

    prefix abc;
    namespace "urn:cesnet:mod3";

    container ccc {
        list ll {
            key "k";

            leaf k { type string; }

            config "true";

            reference "test reference";

            description "test description";

            config false; // duplicated
        }
    }
}
