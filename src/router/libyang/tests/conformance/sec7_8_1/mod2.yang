module mod2 {

    prefix abc;
    namespace "urn:cesnet:mod2";

    container ccc {
        list ll {
            key "k";

            leaf k { type string; }

            reference "test reference";

            description "test description";

            reference "test2"; // duplicated

        }
    }
}
