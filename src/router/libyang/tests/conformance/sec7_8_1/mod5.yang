module mod5 {

    prefix abc;
    namespace "urn:cesnet:mod5";

    container ccc {
        list ll {
            key "k";

            leaf k { type string; }

            max-elements 3;

            config "true";

            reference "test reference";

            description "test description";

            max-elements unbounded; // duplicated

            leaf l { type boolean; }
        }
    }
}
