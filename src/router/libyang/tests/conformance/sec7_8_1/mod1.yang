module mod1 {

    prefix abc;
    namespace "urn:cesnet:mod1";

    container ccc {
        list ll {
            key "k";

            leaf k { type string; }

            description "test description";

            description "test2"; // duplicated

        }
    }
}
