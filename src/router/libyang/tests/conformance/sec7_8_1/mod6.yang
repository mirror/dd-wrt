module mod6 {

    prefix abc;
    namespace "urn:cesnet:mod6";


    list ll {
        key "k";

        leaf k { type string; }

        max-elements 3;

        min-elements 2;

        config "true";

        reference "test reference";

        description "test description";

        min-elements 1; // duplicated

        leaf l { type boolean; }
    }
}
