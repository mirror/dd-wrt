module mod8 {

    prefix abc;
    namespace "urn:cesnet:mod8";


    list ll {
        key "k";

        leaf k { type string; }

        max-elements 3;

        status current;

        min-elements 2;

        ordered-by system;

        config "true";

        reference "test reference";

        description "test description";

        status obsolete; // duplicated

        leaf l { type boolean; }
    }
}
