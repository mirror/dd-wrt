module mod9 {

    prefix abc;
    namespace "urn:cesnet:mod9";

    list ll-top {
        list ll {
            key "k";

            leaf k { type string; }

            max-elements 3;

            status current;

            when "k = 'abc'";

            min-elements 2;

            ordered-by system;

            config "true";

            reference "test reference";

            description "test description";

            when "k = 'password' and ../leaf = 42"; // duplicated

            leaf l { type boolean; }
        }

        key leaf;

        leaf leaf { type uint8; }
    }
}
