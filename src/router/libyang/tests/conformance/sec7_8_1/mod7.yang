module mod7 {

    prefix abc;
    namespace "urn:cesnet:mod7";


    list ll {
        key "k";

        leaf k { type string; }

        max-elements 3;

        min-elements 2;

        ordered-by system;

        config "true";

        reference "test reference";

        description "test description";

        ordered-by "user"; // duplicated

        leaf l { type boolean; }
    }
}
