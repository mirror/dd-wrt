module mod8 {
    prefix abc;
    namespace "urn:cesnet:mod8";

    leaf leaf {
        type decimal64 {
            fraction-digits 2;
            range "0. ..3.2";  // bad decimal number
        }
    }
}
