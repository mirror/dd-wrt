module mod2 {
    prefix abc;
    namespace "urn:cesnet:mod2";

    typedef my {
        type decimal64 {
            fraction-digits 3;
        }
    }

    leaf my1 {
        type my {
            fraction-digits 5;  // not allow double fraction-digits
        }
    }
}
