module mod6 {
    prefix abc;
    namespace "urn:cesnet:mod6";

    typedef my-decimal {
        type decimal64 {
            fraction-digits 2;
            range "1 .. 3.14 | 10 | 20..max";
        }
    }

    leaf my {
        type my-decimal {
            range "0.9 .. 2.12";  // bad min value;
        }
    }
}
