module mod7 {
    prefix abc;
    namespace "urn:cesnet:mod7";

    typedef my-decimal {
        type decimal64 {
            fraction-digits 2;
            range "1 .. 3.14 | 10 | 20..max";
        }
    }

    leaf my {
        type my-decimal {
            range "5.55"; // bad value
        }
    }
}
