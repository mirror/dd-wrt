module mod9 {
    prefix abc;
    namespace "urn:cesnet:mod9";

    leaf leaf {
        type decimal64 {
            fraction-digits 2;
            range "0.1 ..3.";  // bad decimal number
        }
    }
}
