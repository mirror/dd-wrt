module mod10 {
    prefix abc;
    namespace "urn:cesnet:mod10";

    leaf leaf {
        type decimal64 {
            fraction-digits 2;
            range "0.1..3.a";  // bad decimal number
        }
    }
}
