module mod11 {
    prefix abc;
    namespace "urn:cesnet:mod11";

    typedef my-decimal {
        type decimal64 {
            fraction-digits 2;
            range "1 .. 3.14 | 10 | 20..max";
        }
    }

    leaf-list llist {
       type my-decimal;
    }

    leaf-list llist1 {
        type my-decimal {
            range "1.5 .. 2.99 | 25 .. 66.66" {
                error-message "test message";
                error-app-tag "test-tag";
                description "test description";
                reference "test reference";
            }
        }
    }

    leaf leaf {
        type decimal64 {
            fraction-digits 4;
        }

        default "3.1456";
    }
}
