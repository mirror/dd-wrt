module mod2 {

    namespace "urn:cesnet:mod2";
    prefix abc;

    description "This is example text,\nwhich is formatted.";

	reference "This is example text, 					                  
     which is formatted.";

    contact "This is example text,                     
             which is formatted.";

    organization "This is example text,                     
	     which is formatted.";
}
