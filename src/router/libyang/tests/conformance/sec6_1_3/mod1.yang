module mod1 {

    prefix abc;
    namespace "urn:cesnet:mod1";

    description "Test for special characters: { } ; space /* multiple 
                 line comment */ // comment";
    reference 'Test for special characters: { } ; space /* multiple line comment */ // comment';

    contact "\"" + '"' +  ' \\' + " \\ " + " \n" + "\t " + ' \n' + '\t ';

    organization "Test for special"
    + " characters: { } ; space "  +    "/* multiple 
                                      line comment */ // comment";
}
