module mod1 {
    prefix abc;
    namespace "urn:cesnet:mod1";

    choice ch1 {
        default "login";

        case ca {
            list server {
                key "name";
                unique "ip port";
                leaf name {
                    type string;
                }
                leaf ip {
                    type string {
                        pattern '[0-9\.]*';
                    }
                }
                leaf port {
                    type uint16;
                }
            }
            description "test case";
        }

        container login {
            leaf login { type string; }

            leaf password {
                type string {
                    length "6..64";
                }
            }
        }

        mandatory true;
    }
}
