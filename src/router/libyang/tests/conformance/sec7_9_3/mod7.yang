module mod7 {
    prefix abc;
    namespace "urn:cesnet:mod7";

    grouping g {
        typedef my {
            type string {
                pattern "[a-zA-Z]+";
            }
        }
        uses gg;
    }

    choice ch1 {
        default "login";

        container login {
            leaf login { type string; }

            leaf password {
                type string {
                    length "6..64";
                }
            }

            container ssh {
                container cont {
                    container ccc;

                    uses g;
                }
            }
        }
    }

    grouping gg {
        container ff {
            anyxml any {
                mandatory true;

                description "mandatory node";
            }
        }


    }
}
