module mod6 {
    prefix abc;
    namespace "urn:cesnet:mod6";

    choice ch1 {
        default "login";

        container login {
            leaf login { type string; }

            leaf password {
                type string {
                    length "6..64";
                }
            }

            container ssh {
                container presence {
                    list list {
                        key keys;

                        leaf keys { type int32; }
                        min-elements 10;
                        max-elements 15;
                    }
                    presence "enable";
                }
            }
        }
    }
}
