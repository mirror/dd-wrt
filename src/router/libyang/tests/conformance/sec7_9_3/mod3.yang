module mod3 {
    prefix abc;
    namespace "urn:cesnet:mod3";

    container cont {
        choice ch1 {
            default ca1;

            case ca1 {
                description "test case";

                leaf name {
                    type string {
                        pattern '[a-zA-Z]+';
                    }
                    default "AdamPC";
                }
            }

            container ssh {
                presence "enable";
            }
        }
    }

    choice ch2 {
        case login {
            leaf login { type string; }

            leaf password {
                type string {
                    length "6..64";
                }
                default "admin123";
            }
        }
    }

    leaf test { type uint8; }
}
