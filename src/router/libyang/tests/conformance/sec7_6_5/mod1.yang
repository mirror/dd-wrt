module mod1 {

    prefix abc;
    namespace "urn:cesnet:mod1";

    container ll {
        leaf leaf1 {
            type aaa;
            mandatory flase;
        }
    }

    typedef aaa {
        type string;
    }
}
