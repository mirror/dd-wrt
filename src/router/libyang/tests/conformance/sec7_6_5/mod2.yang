module mod2 {
    prefix abc;
    namespace "urn:cesnet:mod2";

    leaf aa {
        type string;
        mandatory "true";
    }

    container ccc {
        leaf aa {
            type uint8;
            mandatory true;
        }
    }

    list list{
        key "input";

        leaf leaf {
            type int16;
            mandatory true;
        }

        leaf input {
            type string;
        }
    }

    choice bbb {
        container cont {
            typedef abc {
                type uint8;
                default 42;
            }

            container presence {
                presence "enable";

                leaf mandatory {
                    type string;
                    mandatory "true";
                }
            }
        }

        leaf leaf1 {
            mandatory false;
            type boolean;
        }

        case aaa {
            leaf leaf8 {
                type uint8;
            }
            leaf mandatory {
                type int16;
                mandatory true;
            }
        }
    }

    leaf abc {
        type int16;
        mandatory "false";
    }
}
