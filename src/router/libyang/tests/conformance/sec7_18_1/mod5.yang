module mod5 {
    prefix abc;
    namespace "urn:cesnet:mod5";

    feature f2;

    feature f1 {
        reference "test reference";
        description "test description";

        if-feature f3;
        if-feature f2;
    }

    feature f3 {
        status current;

        if-feature f4;
    }

    feature f4 {
        if-feature f1; // reference itself indirectly
    }
}
