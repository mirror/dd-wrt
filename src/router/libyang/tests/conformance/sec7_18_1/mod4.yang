module mod4 {
    prefix abc;
    namespace "urn:cesnet:mod4";

    feature f2;

    feature f1 {
        reference "test reference";
        description "test description";

        if-feature f1; // reference itself
    }
}
