module mod3 {
    prefix abc;
    namespace "urn:cesnet:mod3";

    feature f1 {
        reference "test reference";
        status current;
        description "test description";

        status obsolete; // duplicated
    }
}
