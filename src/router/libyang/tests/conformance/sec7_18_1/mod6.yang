module mod6 {
    prefix abc;
    namespace "urn:cesnet:mod6";

    feature f1 {
        if-feature f2;
        description "test description";
        reference "test reference";
        status current;
    }

    feature f2 {
        if-feature f3;
        if-feature f4;
    }

    feature f3;

    feature f4 {
        description "test1";
    }
}
