module mod5 {
    prefix abc;
    namespace "urn:cesnet:mod5";

    container ccc {
        anyxml any {
            config true;
            status obsolete;
            mandatory true;
            reference "test reference";
            description "test description";

            status "current";// duplicated
        }
    }
}
