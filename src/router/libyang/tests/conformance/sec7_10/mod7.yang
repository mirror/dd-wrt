module mod7 {
    prefix abc;
    namespace "urn:cesnet:mod7";

    feature f1;

    container ccc {
        anyxml any {
            if-feature f1;

            must "../../name = 'server'";
        }
    }

    leaf top {
        type string;
        default "admin";
    }

    leaf name { type string; }

    augment "/ccc/any" {
        container ssh {
            presence enable;
        }
    }

}
