module mod8 {
    prefix abc;
    namespace "urn:cesnet:mod8";

    feature f1;

    container ccc {
        anyxml any {
            when "/top = 'admin'";
            if-feature f2;
            config true;
            status current;
            mandatory true;
            reference "test reference";
            description "test description";

            if-feature f1;

            must "../../cont/error = 42";
            must "../../name = 'server'";
        }
    }

    leaf top {
        type string;
        default "admin";
    }

    leaf name { type string; }

    container cont {
        leaf error { type uint8; }
    }

    anyxml unknown {
        if-feature f2;
    }

    feature f2;
}
