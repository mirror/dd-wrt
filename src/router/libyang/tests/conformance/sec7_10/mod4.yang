module mod4 {
    prefix abc;
    namespace "urn:cesnet:mod4";

    container ccc {
        anyxml any {
            config true;
            mandatory true;
            reference "test reference";
            description "test description";

            mandatory "false";// duplicated
        }
    }
}
