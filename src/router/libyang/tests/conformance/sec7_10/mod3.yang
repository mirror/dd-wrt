module mod3 {
    prefix abc;
    namespace "urn:cesnet:mod3";

    container ccc {
        anyxml any {
            config true;
            reference "test reference";
            description "test description";

            config "false";// duplicated
        }
    }
}
