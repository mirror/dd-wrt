module mod2 {
    prefix abc;
    namespace "urn:cesnet:mod2";

    anyxml any {
        reference "test reference";
        description "test description";

        reference "test";// duplicated
    }
}
