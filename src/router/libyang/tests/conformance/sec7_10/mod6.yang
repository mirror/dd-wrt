module mod6 {
    prefix abc;
    namespace "urn:cesnet:mod6";

    container ccc {
        anyxml any {
            when "/top = 'admin'";
            config true;
            status obsolete;
            mandatory true;
            reference "test reference";
            description "test description";

            when "/top = 'admin'"; // duplicated
        }
    }

    leaf top {
        type string;
        default "admin";
    }
}
