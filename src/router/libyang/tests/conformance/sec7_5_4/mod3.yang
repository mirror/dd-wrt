module mod3 {

    prefix abc;
    namespace "urn:cesnet:mod3";

    container interface {
        leaf ifType {
            type enumeration {
                enum ethernet;
                enum atm;
            }
        }

        leaf ifMTU {
            type uint32;
        }

        must "ifType != 'ethernet' or " +
             "(ifType = 'ethernet' and ifMTU = 1500)" {
            description "Test description";
            error-app-tag "Error 750";
            error-message "An ethernet MTU must be 1500";
            description "Duplicated string";

        }
        must "ifType != 'atm' or " +
             "(ifType = 'atm' and ifMTU <= 17966 and ifMTU >= 64)" {
            error-message "An atm MTU must be  64 .. 17966";
        }
    }
}
