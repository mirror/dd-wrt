module mod4 {

    prefix abc;
    namespace "urn:cesnet:mod4";

    container interface {

        must "ifType != 'atm' or " +
             "(ifType = 'atm' and ifMTU <= 17966 and ifMTU >= 64)" {
            error-message "An atm MTU must be  64 .. 17966";
            reference "Test reference.";
        }

        leaf ifType {
            type enumeration {
                enum ethernet;
                enum atm;
            }
        }

        leaf ifMTU {
            type uint32;
        }

        must "ifType != 'ethernet' or " +
             "(ifType = 'ethernet' and ifMTU = 1500)" {
            description "Test description";
            reference "Test reference";
            error-app-tag "Error 750";
            error-message "An ethernet MTU must be 1500";
            reference "Duplicated string";

        }
    }
}
