module mod1 {
    prefix abc;
    namespace "urn:cesnet:mod1";

    container presence {
        presence "enable";
        container cont {}
    }

    leaf test {
        type boolean;
    }

    augment "/presence/cont" {
        leaf default {
            type string;
            default default;
        }

        when "../../test = 'true'";  // context augment target
    }

    augment "/presence" {
        container augment {
            leaf test {
                type boolean;
            }
        }

        when "/test = 'true'";
    }
}
