module mod2 {
    prefix abb;
    namespace "urn:cesnet:mod2";

    container ccc {
        leaf test {
            type boolean;
        }
    }

    choice ch1 {
        case ca {
            container ssh {
                presence "enable";
            }
        }

        leaf-list llist {
            type int8;
        }

        when "/ccc/test";
    }

    container cont {
        choice ch1 {
            case ca {
                container ssh {
                    presence "enable";
                }
            }

            leaf-list llist {
                type int8;
            }

            when "../ccc/test";
        }
    }

    choice ch2 {
        case ca {
            leaf leaf_2 {
                type string;
            }
        }

        leaf leaf_3 {
            type uint8;
        }

        when "ccc/test = 'true'";
    }

    container cont2 {
        choice ch3 {
            case ca {
                choice ch4 {
                    case cb {
                        leaf leaf {
                            type string;
                        }
                    when "../ccc/test = 'true'";
                    }
                }
            }
        }
    }
}
