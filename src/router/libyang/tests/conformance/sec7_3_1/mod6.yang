module mod6 {

    prefix abc;
    namespace "urn:cesnet:mod6";

    typedef my_type {
        type uint32;
        default "42";
        reference "test reference";
        status "current";
        type string;
    }
}
