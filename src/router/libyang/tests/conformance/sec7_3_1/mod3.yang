module mod3 {

    prefix abc;
    namespace "urn:cesnet:mod3";

    typedef my_type {
        reference "duplicated string";
        type uint32;
        default 10;
        description "test1";
        reference "test2";
    }
}
