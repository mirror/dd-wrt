module mod8 {

    prefix mm;
    namespace "urn:cesnet:mod8";

    typedef td1 {
        type string;
        default "aaa";
    }

    typedef td2 {
        type uint8;
        default "128";
        description "Test description";
    }

    typedef td3 {
        description "Test description";
        type uint32;
        reference "Test reference";
        default "128";
    }

    typedef td4 {
        type uint16;
        reference "Test reference";
        default "128";
        description "Test description";
        units "kilograms";
    }

    typedef td5 {
        reference "Test reference";
        description "Test description";
        default "128";
        status current;
        units "kilograms";
        type int16;
    }

    container ccc {
        typedef tt {
            type td5;
            description "Test";
        }

        container bbb {
            grouping gg {
                typedef t1 {
                    type tt;
                    units "avc";
                }

                typedef t2 {
                    type t1;
                }

                typedef t3 {
                    type td3;
                    default 10;
                }
            }
        }
    }

}
