module mod7 {

    prefix abc;
    namespace "urn:cesnet:mod7";

    typedef my_type {
        type uint32;
        units "kilograms";
        default "42";
        reference "test reference";
        status "current";
        units "megabyte";
    }
}
