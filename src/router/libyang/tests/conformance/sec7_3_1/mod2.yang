module mod2 {

    prefix abc;
    namespace "urn:cesnet:mod2";

    typedef my_type {
        type uint32;
        description "test";
        default 10;
        description "duplicated string";
    }
}
