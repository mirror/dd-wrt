module mod3 {
    prefix abc;
    namespace "urn:cesnet:mod3";

    notification not {
        reference "test reference";
        status current;
        description "test description";

        status "obsolete"; // duplicated
    }
}
