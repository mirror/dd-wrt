module mod1 {
    prefix abc;
    namespace "urn:cesnet:mod1";

    container cont {
        choice ch1 {
            mandatory true;

            description " test description";

            case ca {
                leaf name {
                    type string;
                    default "AdamPC";
                }

                leaf error { type int8; }
            }

            container ssh {
                presence "enable";
            }
        }

        leaf test { type uint8; }
    }

    container presence {
        presence "enable";

        choice ch2 {
            mandatory true;

            description " test description";

            case ca {
                leaf name {
                    type string;
                    default "EvaPC";
                }

                leaf error { type int8; }
            }

            container ssh {
                presence "enable";
            }
        }
    }

    choice ch3 {
        case mand {
            leaf test { type uint8; }

            choice ch1 {
                mandatory true;

                description " test description";

                case ca {
                    leaf name {
                        type string;
                        default "RomanPC";
                    }

                    leaf error { type int8; }
                }

                container ssh {
                    presence "enable";
                }
            }
        }
    }

    leaf number { type uint8; }
}
