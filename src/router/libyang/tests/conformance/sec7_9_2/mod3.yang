module mod3 {
    prefix abc;
    namespace "urn:cesnet:mod3";

    container ccc {
        choice ch1 {
            case ca {
                status deprecated;

                reference "test reference";

                description "test description";

                status obsolete; // duplicated
            }

            reference "test reference";
        }

        description "test description 2";
    }
}
