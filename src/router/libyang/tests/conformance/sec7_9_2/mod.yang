module mod {
    prefix m;
    namespace "urn:cesnet:mod";

    feature f1;

    grouping login {
        leaf login {
            type string {
                pattern '[a-zA-Z][a-zA-Z_0-9]*';
            }
        }

        leaf password {
            type string {
                length "5..255";
            }
            default "admin";
        }
    }
}
