module mod7 {
    prefix abc;
    namespace "urn:cesnet:mod7";

    container ccc {
        choice ch1 {
            container hide {
                leaf name { type string; }

                leaf enabled { type boolean; }
            }

            case hide { // duplicated case hide
                leaf test { type string; }
            }
        }
    }
}
