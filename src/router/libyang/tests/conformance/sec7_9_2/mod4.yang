module mod4 {
    prefix abc;
    namespace "urn:cesnet:mod4";

    container ccc {
        choice ch1 {
            case ca {
                status deprecated;

                when "/top = 'admin'";

                reference "test reference";

                description "test description";

                when "/top = 'admin'"; // duplicated
            }

            reference "test reference";
        }

        description "test description 2";
    }

    leaf top {
        type string;
        default "admin";
    }
}
