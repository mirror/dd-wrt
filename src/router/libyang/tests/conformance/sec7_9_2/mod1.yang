module mod1 {
    prefix abc;
    namespace "urn:cesnet:mod1";

    container ccc {
        choice ch1 {
            case ca {
                description "test description";

                description "test"; // duplicated
            }

            reference "test reference";
        }

        description "test description 2";
    }
}
