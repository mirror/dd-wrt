module mod6 {
    prefix abc;
    namespace "urn:cesnet:mod6";

    import mod {
        prefix mod;
    }

    grouping server {
        list server {
            key "name";
            unique "ip port";
            leaf name {
                type string;
            }
            leaf ip {
                type string {
                    pattern '[0-9\.]*';
                }
            }
            leaf port {
                type uint16;
            }
        }
    }

    container cont {
        choice ch1 {
            case ca {
                anyxml anyxml1;
                description "test description";
                reference "test reference";

                anyxml anyxml2;
                if-feature mod:f1;

                uses mod:login;

                uses server;

                leaf enabled {
                    type boolean;
                }
            }

            case cb {
                reference "test reference";

                leaf-list name { type string; }

                container presence {
                    presence "enable";
                }

                list ll4 {
                    key "bb";

                    leaf bb {
                        type uint32;
                    }
                }
            }

            case cc {
                choice ch2 {
                    container ssh_login {
                        uses mod:login;
                    }
                }
                if-feature f2;
            }

            leaf-list test { type string; }
        }
    }

    feature f2;
}
