module mod2 {
    prefix abc;
    namespace "urn:cesnet:mod2";

    container ccc {
        choice ch1 {
            case ca {
                reference "test reference";

                description "test description";

                reference "test"; // duplicated
            }

            reference "test reference";
        }

        description "test description 2";
    }
}
