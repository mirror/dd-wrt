module mod5 {
    prefix abc;
    namespace "urn:cesnet:mod5";

    choice interface-type {     // This example is illegal YANG
         case a {
             leaf ethernet { type string; }
         }
         case b {
             container ethernet {
                leaf ip {
                    type string;
                }
             }
         }
     }
}
