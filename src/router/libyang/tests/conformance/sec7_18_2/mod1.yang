module mod1 {
    prefix abc;
    namespace "urn:cesnet:mod1";

    import mod3 {
        prefix mod;
    }

    include sub1;

    feature f1;

    feature f2 {
        if-feature f3;
    }

    feature f4 {
        if-feature f2;
    }

    container ccc {
        leaf empty { type empty; }
        if-feature f2;
    }

    container mod {
        leaf leaf { type uint8; }
        if-feature mod:f2;
    }
}
