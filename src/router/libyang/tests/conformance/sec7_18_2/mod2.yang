module mod2 {
    prefix abb;
    namespace "urn:cesnet:mod2";

    feature f1 {
        description "test";
    }

    feature f2 {
        if-feature f1;
    }

    feature f3 {
        if-feature f2;
        if-feature f4;        // not found f4
    }
}
