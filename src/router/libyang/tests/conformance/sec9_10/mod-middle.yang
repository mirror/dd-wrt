module mod-middle {
  namespace urn:cesnet:mod-middle;
  prefix mm;

  import mod {
    prefix m;
  }

  identity j4 {
    base m:j1;
  }

  typedef j {
    type identityref {
      base m:j1;
    }
    default m:j3;
  }
}
