submodule sub3 {
    belongs-to mod3 {
        prefix sub;
    }

    import mod {
        prefix mod;
    }

    identity sub;

    identity sub2 {
        base mod:j1;
    }

    identity k1 {
        base sub2;
    }
}
