module mod2 {
    prefix abc;
    namespace "urn:cesnet:mod1";

    typedef my {
        type identityref {
            // missing base statement;
        }
    }

    leaf leaf {
        type my;
    }

    identity i1 {
        description "abc";
    }

    identity i3;
}
