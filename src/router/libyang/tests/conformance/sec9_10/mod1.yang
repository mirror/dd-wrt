module mod1 {
    prefix abc;
    namespace "urn:cesnet:mod1";

    typedef my {
        type identityref {
            base "abc:i1";
        }
    }

    leaf leaf {
        type my {
            base i3;    // identityref cannot be restricted
        }
    }

    identity i1 {
        description "abc";
    }

    identity i3;
}
