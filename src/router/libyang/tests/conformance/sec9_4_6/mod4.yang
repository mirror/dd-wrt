module mod4 {
    prefix abc;
    namespace "urn:cesnet:mod4";

    typedef my {
        type string {
            pattern '[A-Za-z]+' {
                description "test description";
                reference "test";
            }

            pattern '[a-z]+' {
                reference "test reference";
                error-app-tag "test tag";
                description "test description";
                error-message "test error message";

                error-message "test"; // duplicated
            }
        }
    }
}
