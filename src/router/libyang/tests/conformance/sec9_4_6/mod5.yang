module mod5 {
    prefix abc;
    namespace "urn:cesnet:mod5";

    typedef my {
        type string;
    }

    container cont {
        typedef my2 {
            type my {
                pattern '[a-zA-Z]+';
            }
        }

        leaf leaf1 {
            type my;
        }

        leaf leaf2 {
            type my2 {
                pattern '[a-z]*';
            }
        }

        leaf leaf3 {
            type my4;
        }

        typedef my4 {
            type my3 {
                pattern 'aaa.*';
                pattern 'aaab.*';
            }
        }

        typedef my3 {
            type my2 {
                pattern '[a-z]*' {
                    reference "test reference";
                    error-app-tag "test tag";
                    description "test description";
                    error-message "test error message";
                }
            }
        }

        leaf leaf4 {
            type my2;
        }
    }
}
