module mod2 {
    prefix abc;
    namespace "urn:cesnet:mod2";

    typedef my {
        type string {
            pattern '[A-Za-z]+' {
                description "test description";
                reference "test";
            }

            pattern '[a-z]+' {
                reference "test reference";
                error-app-tag "test tag";
                description "test description";

                error-app-tag "test"; // duplicated
            }
        }
    }
}
