module mod1 {
    prefix abc;
    namespace "urn:cesnet:mod1";

    typedef my {
        type string {
            pattern '[A-Za-z]+' {
                description "test description";
                reference "test";
            }

            pattern '[a-z]+' {
                description "test description";

                description "test"; // duplicated
            }
        }
    }
}
