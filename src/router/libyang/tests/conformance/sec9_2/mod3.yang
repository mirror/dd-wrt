module mod3 {
    prefix abc;
    namespace "urn:cesnet:mod3";

    typedef my1 {
        type uint16 {
            range "10 .. 100" {
                reference "test reference";
                description "test description";
                error-app-tag "test tag";

                error-app-tag "test"; // duplicated
            }
        }
    }
}
