module mod2 {
    prefix abc;
    namespace "urn:cesnet:mod2";

    typedef my1 {
        type uint16 {
            range "10 .. 100" {
                reference "test reference";
                description "test description";

                reference "test"; // duplicated
            }
        }
    }
}
