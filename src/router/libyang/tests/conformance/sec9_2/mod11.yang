module mod11 {
    prefix abc;
    namespace "urn:cesnet:mod11";

    typedef my_type {
        type uint8;
    }

    leaf l1 {
        type "my_type" {
            range "min .. 15 | min .. 50";
        }
    }
}
