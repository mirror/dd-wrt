module mod8 {
    prefix abc;
    namespace "urn:cesnet:mod8";

    leaf leaf {
        type my_type {
            range "min..256";
        }
    }

    typedef my_type {
        type uint8;
    }
}
