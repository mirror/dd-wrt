module mod1 {
    prefix abc;
    namespace "urn:cesnet:mod1";

    typedef my1 {
        type uint16 {
            range "10 .. 100" {
                description "test description";

                description "test"; // duplicated
            }
        }
    }
}
