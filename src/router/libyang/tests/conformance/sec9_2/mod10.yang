module mod10 {
    prefix abc;
    namespace "urn:cesnet:mod10";

    typedef my_type {
        type uint8;
    }

    leaf l1 {
        type "my_type" {
            range "min .. 10 | 11 ..50 | 20 .. 25";
        }
    }
}
