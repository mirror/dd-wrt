module mod13 {
    prefix abc;
    namespace "urn:cesnet:mod13";

    typedef my {
        type int16 {
            range "min .. 6000";
        }
    }

    typedef my_2 {
        type my {
            range "-6000 .. max";
        }
    }

    leaf leaf1 {
        type my;
    }

    leaf leaf2 {
        type my_2;
    }

    leaf-list lleaf1 {
        type my_2 {
            range "min .. -100 | -55 .. 100 | 101 .. max";
        }
    }

    container cont {
        leaf leaf1 {
            type int8 {
                range "min .. max";
            }
        }

        leaf leaf2 {
            type int32 {
                range "min .. max";
            }
        }

        leaf leaf3 {
            type int64 {
                range "min .. max";
            }
        }

        leaf leaf4 {
            type uint8 {
                range "min .. max";
            }
        }

        leaf leaf5 {
            type uint16 {
                range "min .. max";
            }
        }

        leaf leaf6 {
            type uint32 {
                range "min .. max";
            }
        }

        leaf leaf7 {
            type uint64 {
                range "min .. max";
            }
        }
    }
}
