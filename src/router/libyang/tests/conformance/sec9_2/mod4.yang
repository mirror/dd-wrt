module mod4 {
    prefix abc;
    namespace "urn:cesnet:mod4";

    typedef my1 {
        type uint16 {
            range "10 .. 100" {
                description "test description";
                reference "test reference";
                error-message "test error message";
                error-app-tag "test tag";


                error-message "test"; // duplicated
            }
        }
    }
}
