module mod9 {
    prefix abc;
    namespace "urn:cesnet:mod9";

    typedef my_type {
        type uint8;
    }

    leaf l1 {
        type "my_type" {
            range "min .. 10 | 10 ..50";
        }
    }
}
