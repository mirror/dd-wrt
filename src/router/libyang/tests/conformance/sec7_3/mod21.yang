module mod21 {

    prefix mm;
    namespace "urn:cesnet:mod21";

    include sub21;

    container ccc {
        leaf aaa {
            type test;
        }

        container cc {
            list aa {
                key bb;
                choice ch {
                    container c {
                        grouping g{
                            typedef tb {
                                type tt;
                                units "test";
                            }

                            leaf l1 {
                                type tb;
                            }

                            leaf l2{
                                type test;
                            }
                        }
                        leaf bbb {type string;}

                        typedef tt {
                            type test;
                        }
                    }
                    case h {
                        container d {
                            typedef tq {
                                type test;
                            }
                        }
                    }
                }

                leaf bb {type string;}
            }
        }
    }
}
