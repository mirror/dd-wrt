submodule sub21 {

    belongs-to mod21 {
        prefix sub;
    }

    typedef test {
        type decimal64 {
            fraction-digits 3;
        }
    }

    leaf login {
        type string {
            length "8";
            pattern 'x[a-z]{5}[0-9]{2}';
        }
    }
}
