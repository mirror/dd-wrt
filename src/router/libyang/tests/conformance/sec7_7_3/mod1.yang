module mod1 {

    prefix abc;
    namespace "urn:cesnet:mod1";

    leaf-list test {
        type string {
            length "1..9";
            pattern '[0-9]+';
        }

        min-elements -1;
    }
}
