module mod3 {

    prefix abc;
    namespace "urn:cesnet:mod3";

    leaf-list l1 {
        type string;

        min-elements 2;
    }

    choice ch1 {
        case abc {
            leaf-list l2 {
                type int32;
                min-elements 3;
            }

            container presence {
                presence "enable";
            }
        }

        leaf-list l3 {
            type string;

            min-elements 2;
        }

        case abb {
            container ccc {
                leaf-list l4 {
                    min-elements 3;

                    type int16;
                }
                presence "enable";
            }
        }
    }

    container ssh {
        presence "enable";
    }
}
