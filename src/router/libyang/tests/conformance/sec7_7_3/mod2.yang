module mod2 {

    prefix abc;
    namespace "urn:cesnet:mod2";

    container ccc {
        leaf-list test {
            type string {
                length "1..9";
                pattern '[0-9]+';
            }

            min-elements "-1";
        }
    }
}
