module mod5 {

    prefix abc;
    namespace "urn:cesnet:mod5";

    leaf-list l1 {
        type string;

        max-elements 2;
    }

    container cont {
        leaf-list l2 {
            type int32;

            max-elements 1;
        }
    }

    container presence {
        leaf-list l3 {
            type boolean;

            max-elements 1;
            min-elements 1;
        }

        presence "enable";
    }

    choice ch1 {
        case abc {
            leaf-list l4 {
                type uint8;

                max-elements 3;
            }

            container mandatory {
                presence "enable2";
            }
        }

        leaf-list l5 {
            type string;

            max-elements 2;
        }
    }

    leaf-list numbers {
        type uint8;

        max-elements 1024;
        min-elements 1025;
    }
}
