module mod6 {
    prefix abc;
    namespace "urn:cesnet:mod6";

    rpc test {
        grouping setup {
            container setup1 {
                leaf hostname { type string; }

                leaf time-format {
                    type enumeration {
                        enum 12H {
                            value "1";
                        }
                        enum 24H {
                            description "test";
                        }
                    }
                }
            }
        }

        reference "test reference";

        input {
            uses setup;
            uses gr;
        }

        typedef t_user {
            type string {
                pattern '[a-zA-Z]+';
                length "5..64";
            }
            default 'admin';
        }

        grouping gr {
            container login {
                leaf user {
                    type t_user;
                }

                leaf password {
                    type string {
                        length "6..32";
                    }
                }
            }
        }

        output {
            uses gr {
                description "test uses";
            }
        }

        description "test description";
    }

    rpc test2 {
        description "test description";
        reference "test reference";
        status obsolete;
    }

    rpc test3 {
        input {
            leaf key {
                type uint8;
            }
        }
    }
}
