module mod4 {
    prefix abc;
    namespace "urn:cesnet:mod4";

    rpc test {
        reference "test reference";

        output {
            leaf k { type string; }
        }

        description "test description";

        output {
            leaf-list k {
                type string;
                min-elements 2;
                max-elements 10;
            }
        } // duplicated
    }
}
