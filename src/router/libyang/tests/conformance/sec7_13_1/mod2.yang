module mod2 {
    prefix abc;
    namespace "urn:cesnet:mod2";

    rpc test {
        reference "test reference";
        description "test description";

        reference "test"; // duplicated
    }
}
