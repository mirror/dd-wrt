module mod3 {
    prefix abc;
    namespace "urn:cesnet:mod3";

    rpc test {
        reference "test reference";
        status current;
        description "test description";

        status "obselete"; // duplicated
    }
}
