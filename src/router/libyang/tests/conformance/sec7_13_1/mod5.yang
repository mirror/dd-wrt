module mod5 {
    prefix abc;
    namespace "urn:cesnet:mod5";

    rpc test {
        reference "test reference";

        input {
            leaf k { type string; }
        }

        description "test description";

        input {
            leaf-list k {
                type string;
                min-elements 2;
                max-elements 10;
            }
        } // duplicated
    }
}
