module mod {
    prefix m;
    namespace "urn:cesnet:mod";

    grouping login {
        leaf user {
            type string {
                pattern '[A-Za-z]+';
            }
        }

        leaf password {
            type string {
                length "6..255";
            }
        }
    }

    container cont {
        uses login;
    }

    choice ch1 {
        case ca {
            leaf l1 { type uint8; }
        }

        leaf-list ll1 { type string; }
    }

    leaf test1 {
        type boolean;
    }

    leaf not-supported {
        type string;
    }
}
