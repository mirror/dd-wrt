module mod2 {
    prefix abc;
    namespace "urn:cesnet:mod2";

    import mod {
        prefix mod;
    }

    deviation "/mod:cont/mod:user" {
        reference "deviation reference";
        description "deviation description";

        deviate not-supported;
        reference "test"; // duplicated
    }
}
