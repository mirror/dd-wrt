module mod5 {
    prefix acc;
    namespace "urn:cesnet:mod5";

    import mod {
        prefix mod;
    }

    deviation "/mod:test1" {
        deviate add {
            must "../cont/password = 'admin123'";
        }
    }

    deviation "/mod:ch1/mod:ll1/mod:ll1" {
        deviate add {
            max-elements 12;
        }
    }

    deviation "/mod:not-supported" {
        deviate not-supported;
    }
}
