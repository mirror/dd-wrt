module mod4 {
    prefix abc;
    namespace "urn:cesnet:mod4";

    import mod {
        prefix mod;
    }

    deviation "/mod:cont/mod:user" {
        description "test description";
        reference "test reference";

        deviate add {
            config true;
        }
    }

    deviation "/mod:cont/mod:password" {
        description "test description";
        reference "test reference";

        deviate add {
            default "admin123";
        }
    }

    deviation "/mod:test1" {
        deviate add {
            must "../cont/user = 'admin'";
        }
    }
}
