module mod1 {

    prefix abc;
    namespace "urn:cesnet:mod1";

    typedef my {
        type string {
            length "4..10";
        }
    }

    leaf leaf1 {
        type my;
    }

    leaf leaf2 {
        type number;
    }

    container ccc {
        leaf leaf1 {
            type number {
                range "min .. 255";
            }
        }

        leaf leaf2 {
            type number {
                range "256 .. max";
            }
        }

        leaf leaf3 {
            type number {
                range " min .. max";
            }
        }
    }

    typedef number {
        type int32 {
            range "1..1000";
        }

        description "test";
    }
}
