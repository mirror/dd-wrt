module mod11 {
    prefix abc;
    namespace "urn:cesnet:mod11";

    import mod {
        prefix mod;
    }

    augment "/mod:cont/mod:ch2" {
        leaf-list llist {
            type string;
        }

        case cb {
            leaf error {
                type int8;
            }
        }
    }
}
