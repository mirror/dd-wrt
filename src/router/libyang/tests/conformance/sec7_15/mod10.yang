module mod10 {
    prefix abb;
    namespace "urn:cesnet:mod10";

    augment "/login" {
        leaf password {
            type string {
                length "6..64";
            }
        }
    }

    container login {
        leaf user {
            type string {
                pattern '[a-z]+';
            }
        }
    }

    container cont {
        choice ch1 {
            case ca {
                leaf test1 { type string; }
            }

            leaf test2 { type boolean; }
        }
    }

    augment "/abb:cont/ch1" {
        case cb {
            leaf test3 { type empty; }
        }

        leaf test4 { type uint8; }
    }

    augment "/cont" {
        leaf test5 {
            type enumeration {
                enum one {
                    value 1;
                }
                enum two;
                enum tree;
            }
        }
    }

    notification notif1 {
        container cont {
            leaf-list llist {
                type uint8;
                min-elements 2;
                max-elements 5;
            }
        }
    }

    augment "/notif1/cont" {
        leaf leaf {
            type boolean;
        }
    }
}
