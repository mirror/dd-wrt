module mod {
    prefix m;
    namespace "urn:cesnet:mod";

    description "global description";
    reference "global reference";

    container server {
        leaf name {
            type string;
        }
    }

    choice ch1 {
        case ca {
            container ssh {
                presence "enable";
            }
        }

        leaf-list user {
            type string;
        }
    }

    container cont {
        choice ch2 {
            case cc {
                container presence {
                    presence "enable";
                }
            }
        }
    }
}
