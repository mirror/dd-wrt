module mod7 {
    prefix abc;
    namespace "urn:cesnet:mod7";

    container cont {
        presence "enable";
    }

    augment "/abc:cont" {
        reference "test reference";
        status "current";
        description "test description";

        leaf abc { type string; }
    }

    leaf test {
        type boolean;
    }

    augment "/abc:cont" {
        leaf abc {
            type uint8;
        }
    }
}
