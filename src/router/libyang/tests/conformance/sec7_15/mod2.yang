module mod2 {
    prefix abc;
    namespace "urn:cesnet:mod2";

    container cont {
        presence "enable";
    }

    augment "/abc:cont" {
        reference "test reference";
        description "test description";

        reference "test"; //duplicated
    }
}
