module mod5 {
    prefix abc;
    namespace "urn:cesnet:mod5";

    container cont {
        presence "enable";
    }

    augment "/abc:test" {
        reference "test reference";
        status "current";
        description "test description";

        leaf abc { type string; }
    }

    leaf test {
        type boolean;
    }
}
