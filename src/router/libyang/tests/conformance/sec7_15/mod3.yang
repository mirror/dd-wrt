module mod3 {
    prefix abc;
    namespace "urn:cesnet:mod3";

    container cont {
        presence "enable";
    }

    augment "/abc:cont" {
        reference "test reference";
        status "current";
        description "test description";

        status "deprecated"; //duplicated
    }
}
