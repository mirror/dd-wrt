module mod6 {
    prefix abc;
    namespace "urn:cesnet:mod6";

    container cont {
        presence "enable";
    }

    augment "/abc:cont" {
        reference "test reference";
        status "current";
        description "test description";

        leaf abc { type string; }

        case ca {
            container ssh {
                presence "enable";
            }
        }
    }

    leaf test {
        type boolean;
    }
}
