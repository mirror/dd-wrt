module mod4 {
    prefix abc;
    namespace "urn:cesnet:mod4";

    container cont {
        presence "enable";
    }

    augment "/abc:cont" {
        reference "test reference";
        status "current";
        when "../test = 'true'";
        description "test description";

        when "../test = 'false'"; //duplicated
    }

    leaf test {
        type boolean;
    }
}
