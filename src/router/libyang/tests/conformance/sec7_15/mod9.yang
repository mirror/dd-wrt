module mod9 {
    prefix abc;
    namespace "urn:cesnet:mod9";

    import mod {
        prefix mod;
    }

    augment "/mod:ch1" {
        case cb {
            leaf error {
                type int8;
            }

            leaf-list mand {
                type string;
                min-elements 3;
            }
        }
    }
}
