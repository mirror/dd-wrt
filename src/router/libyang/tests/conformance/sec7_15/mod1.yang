module mod1 {
    prefix abc;
    namespace "urn:cesnet:mod1";

    container cont {
        presence "enable";
    }

    augment "/abc:cont" {
        description "test description";

        description "test"; //duplicated
    }
}
