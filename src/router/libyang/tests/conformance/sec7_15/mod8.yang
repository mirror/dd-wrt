module mod8 {
    prefix abc;
    namespace "urn:cesnet:mod8";

    import mod {
        prefix mod;
    }

    augment "/mod:server" {
        leaf ip {
            type t_ip;
        }

        leaf port {
            type uint16;
        }
    }

    typedef t_ip {
        type string {
            pattern '[0-9]+\.[0-9]+\.[0-9]+\.[0-9]+';
            length "7..15";
        }

        description "ip address";
    }

    augment "/mod:ch1" {
        case cb {
            leaf error {
                type int8;
            }
        }
    }
}
