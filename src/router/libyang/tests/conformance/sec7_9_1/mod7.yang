module mod7 {
    prefix abc;
    namespace "urn:cesnet:mod7";

    container ccc {
        choice ch1 {
            config true;

            mandatory true;

            when "/str = 'string42'";

            status "current";

            reference "test reference";

            description "test description";

            when "/str = 'string42'"; // duplicated

            case ca {
                leaf empty { type empty; }
            }

            case cb {
                container ssh {
                    presence "Enable ssh.";
                }
            }
        }
        description "container description";
    }

    leaf str { type string; }
}
