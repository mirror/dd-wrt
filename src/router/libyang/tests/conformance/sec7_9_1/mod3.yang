module mod3 {
    prefix abc;
    namespace "urn:cesnet:mod3";

    choice ch1 {
        config true;

        reference "test reference";

        description "test description";

        config false; // duplicated
    }
}
