module mod2 {
    prefix abc;
    namespace "urn:cesnet:mod2";

    choice ch1 {
        reference "test reference";
        description "test description";

        reference "test2"; // duplicated
    }
}
