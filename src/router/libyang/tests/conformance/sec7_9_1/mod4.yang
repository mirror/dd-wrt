module mod4 {
    prefix abc;
    namespace "urn:cesnet:mod4";

    choice ch1 {
        config true;

        default ca;

        reference "test reference";

        description "test description";

        default cb; // duplicated

        case ca {
            leaf empty { type empty; }
        }

        case cb {
            container ssh {
                presence "Enable ssh.";
            }
        }
    }
}
