module mod5 {
    prefix abc;
    namespace "urn:cesnet:mod5";

    choice ch1 {
        config true;

        mandatory true;

        reference "test reference";

        description "test description";

        mandatory "false"; // duplicated

        case ca {
            leaf empty { type empty; }
        }

        case cb {
            container ssh {
                presence "Enable ssh.";
            }
        }
    }
}
