module mod8 {
    prefix abb;
    namespace "urn:cesnet:mod8";

    feature f1;

    choice ch1;

    choice ch2 {
        description "test description";
        reference "test reference";

        if-feature f1;

        anyxml anyxml2;

        config true;

        case ca {
            leaf aa { type string; }
        }

        default cc;

        container cc {
            presence "enable";
            choice ch2 {
                leaf a { type string; }
                leaf b { type uint8; }

                mandatory true;
                if-feature f1;
                when "/top";
            }
        }

        if-feature f2;

        leaf-list name { type string; }

        container ccc {
            description "second container";
        }

        leaf-list ll1 { type int32; }

        list l1 {
            key str;

            leaf str { type string; }
        }

        anyxml anyxml1;

        when "/top";
    }

    leaf-list top {
        type boolean;
    }

    feature f2 {
        description "feature f2";
    }
}
