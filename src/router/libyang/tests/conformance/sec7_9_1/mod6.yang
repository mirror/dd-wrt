module mod6 {
    prefix abc;
    namespace "urn:cesnet:mod6";

    container ccc {
        choice ch1 {
            config true;

            mandatory true;

            status "current";

            reference "test reference";

            description "test description";

            status obsolete; // duplicated

            case ca {
                leaf empty { type empty; }
            }

            case cb {
                container ssh {
                    presence "Enable ssh.";
                }
            }
        }
        description "container description";
    }
}
