module mod1 {
    prefix abc;
    namespace "urn:cesnet:mod1";

    typedef my {
        type "enumeration" {
            enum one {
                description "test";
            }

            enum two {
                description "test description";

                description "test"; // duplicated
            }
        }
    }
}
