module mod5 {
    prefix abc;
    namespace "urn:cesnet:mod5";

    typedef my {
        type "enumeration" {
            enum one {
                description "test";
            }

            enum " two" {  // problem leading white space
                reference "test reference";
                description "test description";
                status current;
                value "4";
            }
        }
    }
}
