module mod2 {
    prefix abc;
    namespace "urn:cesnet:mod2";

    typedef my {
        type "enumeration" {
            enum one {
                description "test";
            }

            enum two {
                reference "test reference";
                description "test description";

                reference "test"; // duplicated
            }
        }
    }
}
