module mod7 {
    prefix abc;
    namespace "urn:cesnet:mod7";

    typedef my {
        type "enumeration" {
            enum one {
                description "test";
            }

            enum "" {  // must not empty
                reference "test reference";
                description "test description";
                status current;
                value "4";
            }
        }
    }
}
