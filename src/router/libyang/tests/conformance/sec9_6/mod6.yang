module mod6 {
    prefix abc;
    namespace "urn:cesnet:mod6";

    typedef my {
        type "enumeration" {
            enum one {
                description "test";
            }

            enum "two  " {  // problem trailing white space
                reference "test reference";
                description "test description";
                status current;
                value "4";
            }
        }
    }
}
