module mod4 {
    prefix abc;
    namespace "urn:cesnet:mod4";

    typedef my {
        type "enumeration" {
            enum one {
                description "test";
            }

            enum two {
                reference "test reference";
                description "test description";
                status current;
                value "4";

                value 1; // duplicated
            }
        }
    }
}
