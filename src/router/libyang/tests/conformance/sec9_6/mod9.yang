module mod9 {
    prefix abc;
    namespace "urn:cesnet:mod9";

    typedef my {
        type "enumeration" {
            enum one {
                description "test";
            }

            enum "two" {
                reference "test reference";
                description "test description";
                status current;
                value "4";
            }

            enum three;

            enum four {
                value 2147483648;  // value is bigger than 2147483647
            }
        }
    }
}
