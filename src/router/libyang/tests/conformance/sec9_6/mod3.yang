module mod3 {
    prefix abc;
    namespace "urn:cesnet:mod3";

    typedef my {
        type "enumeration" {
            enum one {
                description "test";
            }

            enum two {
                reference "test reference";
                description "test description";
                status current;

                status "obsolete"; // duplicated
            }
        }
    }
}
