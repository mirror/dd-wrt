module mod8 {
    prefix abc;
    namespace "urn:cesnet:mod8";

    typedef my {
        type "enumeration" {
            enum one {
                description "test";
            }

            enum "two" {
                reference "test reference";
                description "test description";
                status current;
                value "4";
            }

            enum three;

            enum four {
                value -2147483649;  // value is smaller than -2147483648
            }
        }
    }
}
