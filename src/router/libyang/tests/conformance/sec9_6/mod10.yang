module mod10 {
    prefix abc;
    namespace "urn:cesnet:mod10";

    typedef my {
        type "enumeration" {
            enum one {
                description "test";
            }

            enum "two" {
                reference "test reference";
                description "test description";
                status current;
                value "4";
            }

            enum three;

            enum four {
                value 2147483645;
            }

            enum five;

            enum six {
                value 666;
            }

            enum seven;
            enum eight;   // value is bigger than 2147483647
        }
    }
}
