module mod12 {
    prefix abc;
    namespace "urn:cesnet:mod12";

    typedef my {
        type "enumeration" {
            enum unknown {
                value "-2147483648";
                description "test";
            }

            enum zero;

            enum one {
                description "test";
            }

            enum "two" {
                reference "test reference";
                description "test description";
                status current;
                value "4";
            }

            enum three;

            enum four {
                value 2147483645;
            }

            enum five;

            enum six {
                value 666;
            }

            enum seven;
        }
    }

    leaf-list l1 {
        type my;
    }
}
