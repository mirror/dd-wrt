module mod2 {
    prefix abc;
    namespace "urn:cesnet:mod2";

    container ccc {
        grouping gg {
            leaf-list ll1 {
                type string;
                min-elements 10;
            }

            container presence {
                presence "enable";
                description "test description";
            }

            uses login;
        }

        container bbb;

        list list {
            key name;
            unique "ip port";
            leaf name {
                type string;
            }
            leaf ip {
                type string {
                    pattern '[0-9\.]*';
                }
            }
            leaf port {
                type uint16;
            }
            uses login;
        }

        grouping login {

            leaf login { type string; }
            leaf password { type string; }

            uses global;

            uses gg; // circular dependency
        }
    }

    grouping global {
        anyxml any;

        choice ch1 {
            case ca {
                leaf error { type uint8; }
            }

            container ssh {
                presence "enable ssh.";
            }
        }
    }
}
