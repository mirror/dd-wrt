module mod3 {
    prefix abc;
    namespace "urn:cesnet:mod3";

    container cont {
        grouping ggg {
            container ccc;

            uses hhh;
        }

        grouping gg {
            leaf-list ll1 {
                type int32;
            }
            uses g;
        }

        grouping hhh {
            uses gg;
        }

        presence "enable";


        grouping abc {
            anyxml as;

            container fff;

            uses ggg;           // circular dependency
        }

        grouping g {
            anyxml any;
            uses abc;
        }
    }
}
