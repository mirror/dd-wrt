module mod5 {
    prefix abc;
    namespace "urn:cesnet:mod5";

    container ccc {
        grouping gg {
            reference "test reference";
            description "test description";

            reference "test"; // duplicated
        }
    }
}
