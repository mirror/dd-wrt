module mod7 {
    prefix abc;
    namespace "urn:cesnet:mod7";

    import mod {
        prefix mod;
    }

    container ccc {
        leaf gg { type string; }

        grouping gg {
            anyxml any1;

            container bbb {
                description "test";
            }

            anyxml any2 {
                mandatory true;
            }

            leaf l {
                type int8;
                default -15;
            }

            reference "test reference";
        }

        uses global;
    }

    grouping global {
        description "test description";

        grouping second {
            typedef my_str {
                type string;

                default "my";
            }

            leaf code { type code; }

            typedef code {
                type uint8 {
                    range "1..42";
                }
            }

            leaf-list leaflist {
                type my_str;
                max-elements 50;
            }

            uses login;
        }

        container ccc {
            presence "enable";
            uses second;
        }

    }

    grouping login {
        list server {
            key name;
            unique 'url';

            leaf name { type string; }

            leaf url { type string; }
        }

        choice ch1 {
            leaf ssh { type string; }

            container user {
                leaf username { type string; }
                leaf password { type string; }
            }

            mandatory true;
        }

        uses mod:setup;

        description "test login";

        reference my;

        status current;
    }

    uses login;
}
