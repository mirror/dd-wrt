module mod {
    prefix m;
    namespace "urn:cesnet:mod";

    grouping setup {
        container setup {
            leaf hostname { type string; }

            leaf time-format {
                type enumeration {
                    enum 12H {
                        value "1";
                    }
                    enum 24H {
                        description "test";
                    }
                }
            }
        }
    }

    uses setup;
}
