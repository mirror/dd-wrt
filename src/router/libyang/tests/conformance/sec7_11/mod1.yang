module mod1 {
    prefix abc;
    namespace "urn:cesnet:mod1";

    grouping gg {
        container ccc {
            presence "enable";
			uses hh;
            grouping hh {
                list ll {
                    key keys;

                    leaf keys {
                        type string;
                        mandatory true;
                    }
					uses repeat;
                    grouping repeat {
                        typedef abc {
                            type string {
                                pattern '[a-z]+';
                                length "1..255";
                            }
                        }

                        uses gg;  // circular dependency
                    }
                }
            }
        }
    }
}
