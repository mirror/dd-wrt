module mod4 {
    prefix abc;
    namespace "urn:cesnet:mod4";

    container ccc {
        grouping gg {
            description "test description";

            description "test"; // duplicated
        }
    }
}
