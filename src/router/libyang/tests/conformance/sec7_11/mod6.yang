module mod6 {
    prefix abc;
    namespace "urn:cesnet:mod6";

    container ccc {
        grouping gg {
            reference "test reference";
            status current;
            description "test description";

            status "obsolete"; // duplicated
        }
    }
}
