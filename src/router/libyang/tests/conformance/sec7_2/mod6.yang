module mod6 {

    namespace "urn:cesnet:mod6";
    prefix mm;

    include sub6_1;
    include sub6_2;

    organization "ACME Inc.";
        contact
            "Joe L. User

             ACME, Inc.
             42 Anywhere Drive
             Nowhere, CA 95134
             USA

             Phone: +1 800 555 0100
             EMail: joe@acme.example.com";

    description
        "This module defines common ACME types.";

    revision 2007-06-05 {
        description "Initial revision.";
    }

    // definitions follows...

    uses login;
}
