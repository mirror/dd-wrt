submodule sub6_2 {

    belongs-to mod6 {
        prefix abc;
    }

    organization "ACME Inc.";
        contact
            "Joe L. User

             ACME, Inc.
             42 Anywhere Drive
             Nowhere, CA 95134
             USA

             Phone: +1 800 555 0100
             EMail: joe@acme.example.com";

    description
        "This submodule defines common ACME types.";

    revision 2007-06-09 {
        description "Initial revision.";
    }

    // definitions follows...

    grouping login {
        leaf login {
            type string;
        }

        leaf password {
            type string;
        }
    }
}
