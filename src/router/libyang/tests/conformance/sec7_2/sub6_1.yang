submodule sub6_1 {

    belongs-to mod6 {
        prefix qq;
    }

    import mod {
        prefix m;
    }

    organization "ACME Inc.";
        contact
            "Joe L. User

             ACME, Inc.
             42 Anywhere Drive
             Nowhere, CA 95134
             USA

             Phone: +1 800 555 0100
             EMail: joe@acme.example.com";

    description
        "This submodule defines common ACME types.";

    revision "2007-06-08" {
        description "Initial revision.";
    }

    // definitions follows...

    leaf aa {
        type m:hostname;
    }
}
