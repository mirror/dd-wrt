module mod12 {

    prefix abc;
    namespace "urn:cesnet:mod12";

    include sub12;

    import mod {
      prefix mod;
    }

    container ccc {
        leaf l1 { type string;}
        leaf-list ll1 { type empty; }

        list abc {
            leaf l1 { type string;}
            leaf-list ll1 { type empty; }

            key l1;

            anyxml xx;

            grouping cc;

            container cc {
                if-feature mod:f2;
            }

            container ccc {
                if-feature f2;
                choice ss {
                  container cc {
                      typedef tt {
                          type int8;
                      }
                  }

                  case bb {
                    leaf l2 { type string; }
                  }

                  case ss;

                  case xx {
                      description "OK";
                  }
                }
                leaf ll1 { type string; }
            }
        }
    }

    grouping g {
        leaf test1 {
            type mod:hostname;
        }

        grouping gg1 {    
            leaf test2 {
                type hide_hostname;
            }
            uses h;

            
        }

        typedef hide_hostname {
            type string {
                length "0..128";
            }
        }

        grouping gg2 {
            leaf test3 {
                type boolean;
            }
        }
    }
}
