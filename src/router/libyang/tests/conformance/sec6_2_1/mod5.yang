module mod5 {

    prefix abc;
    namespace "urn:cesnet:mod5";

    import mod {
        prefix mod;
    }

    include sub5_1;
    include sub5_2;

    typedef tt {
        type string;
    }

    typedef ta {
        type tt;
    }
}
