module mod8 {
    
    prefix abc;
    namespace "urn:cesnet:mod8";

    include sub8_1;
    include sub8_2;

    grouping aa {
        leaf bb {
            type string {
                length "1..255";
            }
        }
    }
}
