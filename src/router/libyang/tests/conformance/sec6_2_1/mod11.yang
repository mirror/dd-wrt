module mod11 {

    prefix abc;
    namespace "urn:cesnet:mod11";

    container cc {
        choice test {
            container aa {
                leaf l1 {type string;}
                leaf l2 {type string;}
            }

            case ca {
                description "test";
                leaf l1 {type uint8;}
            }
        }

        typedef ta {
            type string;
        }

        choice test1 {
            case ca {
                leaf l3 {type empty;}
            }
        }

        choice test2 {
             container ba {
                leaf l4 {type string;}
                leaf l5 {type string;}
            }

            case bb {
                description "test";
                leaf l6 {type uint8;}
            }

            case ba {
                description "Duplicated case.";
            }
        }
    }
}
