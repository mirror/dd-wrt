module mod {

    prefix abc;
    namespace "urn:cesnet:mod";

    feature f2;

    identity i2;

    typedef tt {
        type uint8 {
            range "1..128";
        }
    }

    typedef hostname {
        type string {
            length "0..255";
        }
    }

    grouping g {
        leaf test1 {
            type hostname;
        }

        grouping gg1 {    
            leaf test2 {
                type hide_hostname;
            }
            uses h;
        }

        grouping gg2 {
            leaf test3 {
                type empty;
            }
        }

        typedef hide_hostname {
            type string {
                length "0..128";
            }
        }
    }

    grouping h {

        leaf abc {
            type abc:hostname;
        }

    }
}
