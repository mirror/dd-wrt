module mod1 {

    namespace "urn:cesnet:mod1";
    prefix abc;

    include sub1_1;
    include sub1_2;
    
    import mod {
        prefix m;
    }

    feature f2 {
        description "first feature";
    }

    leaf f1 {
        type string;
        default "leaf";
    }

    feature f1 {
        description "second feature";
    }
}
