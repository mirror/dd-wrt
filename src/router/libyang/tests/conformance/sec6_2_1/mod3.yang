module mod3 {
    prefix abc;
    namespace "urn:cesnet:mod3";

    include sub3_1;
    include sub3_2;


    identity i1 {
        description "First identity";
    }

    identity i3 {
        description "Second identity";
        base i1;
    }


    identity i4 {
        base i1;
    }
}
