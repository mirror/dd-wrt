module mod10 {

    prefix abc;
    namespace "urn:cesnet:mod10";

    include sub10;

    rpc rr {
        grouping gg {
            leaf l1 {
                type uint32;
            }
        }
    }
    container ccc {
        leaf l1 { type string;}
        leaf-list ll1 { type empty; }

        list abc {
            leaf l1 { type string;}
            leaf-list ll1 { type empty; }

            key l1;

            anyxml xx;

            grouping cc;

            container cc;

            container ccc {
                choice ss {
                  container cc {
                      typedef tt {
                          type int8;
                      }
                  }

                  case bb {
                    leaf l2 { type string; }
                  }
                }
                leaf l2 { type string; }
            }
        }
    }
}
