submodule sub8_2 {

    belongs-to mod8 {
        prefix sj;
    }

    grouping gg {
        leaf aa {
            type uint8;
            default 8;
        }

        container bb {
            leaf l1 {
                type string;
            }

            leaf l2 {
                type string;
            }
        }
    }
}
