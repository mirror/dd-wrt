module mod9 {

    prefix abc;
    namespace "urn:cesnet:mod9";

    grouping aa {
        leaf bb {
            type string {
                length "1..255";
            }
        }

        grouping aa {
            description "Duplicated grouping.";
        }
    }
}
