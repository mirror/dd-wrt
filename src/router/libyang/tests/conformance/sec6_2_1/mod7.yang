module mod7 {

    prefix abc;
    namespace "urn:cesnet:mod7";

    typedef tt {
        type string;
    }

    typedef ta {
        type uint8;
    }

    container cc {
        typedef tc {
            type tt {
                length "1..255";
            }
        }

        leaf aa {
            type tc;
        }

        container ccc {
            typedef tb {
                type union {
                    type string;
                    type int16;
                }
            }
        }
    }

    typedef tb {
        type empty;
    }
}
