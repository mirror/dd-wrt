submodule sub9 {
    
    belongs-to mod10 {
        prefix sk;
    }

    container cc {
        leaf l1 { type string;}
        leaf-list ll1 { type empty; }

        list abc {
            leaf l1 { type string;}
            leaf-list ll1 { type empty; }

            key l1;

            anyxml xx;

            grouping cc;

            container cc;

            container ccc {
                choice ss {
                  container cc {
                      typedef tt {
                          type int8;
                      }
                  }

                  case bb {
                    leaf l2 { type string; }
                  }
                }
                leaf l1 { type string; }
            }
        }
    }
}
