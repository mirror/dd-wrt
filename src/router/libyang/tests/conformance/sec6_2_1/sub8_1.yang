submodule sub8_1 {
    
    belongs-to mod8 {
        prefix sl;
    }

    grouping gg {
        typedef abc {
            type uint8;
        }

        leaf aa {
            type abc;
            default 8;
        }
    }

    container bb {
        leaf l1 {
            type string;
        }

        leaf l2 {
            type string;
        }
    }
}
