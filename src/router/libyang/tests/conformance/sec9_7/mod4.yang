module mod4 {
    prefix abc;
    namespace "urn:cesnet:mod4";

    typedef my {
        type bits {
            bit one {
                description "test";
            }

            bit two {
                description "test description";
                status "current";
                reference "test reference";
                position "1";

                position 20; // duplicated
            }
        }
    }
}
