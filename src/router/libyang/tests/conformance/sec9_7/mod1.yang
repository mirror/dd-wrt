module mod1 {
    prefix abc;
    namespace "urn:cesnet:mod1";

    typedef my {
        type bits {
            bit one {
                description "test";
            }

            bit two {
                description "test description";

                description "test"; // duplicated
            }
        }
    }
}
