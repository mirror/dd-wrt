module mod5 {
    prefix abc;
    namespace "urn:cesnet:mod5";

    typedef my {
        type bits {
            bit one {
                description "test";
            }

            bit "" {  // problem empty bit name
                description "test description";
                status "current";
                reference "test reference";
                position "1";
            }
        }
    }
}
