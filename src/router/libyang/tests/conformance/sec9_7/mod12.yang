module mod12 {
    prefix abc;
    namespace "urn:cesnet:mod12";

    typedef my {
        type bits {
            bit one {
                description "test";
            }

            bit "two" {
                description "test description";
                status "current";
                reference "test reference";
                position "42";
            }

            bit three;

            bit four {
                position 4294967293;
            }

            bit five {
                position 555;
            }

            bit six {
                position 666;
            }

            bit seven;
            bit eight;
        }
    }

    leaf-list test {
        type my;
    }

    leaf mybits {
        type bits {
            bit disable-nagle {
                position 0;
            }
            bit auto-sense-speed {
                position 1;
            }
            bit ten-Mb-only {
                position 2;
            }
        }
        default "auto-sense-speed";
    }
}
