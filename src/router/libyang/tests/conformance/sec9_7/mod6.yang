module mod6 {
    prefix abc;
    namespace "urn:cesnet:mod6";

    typedef my {
        type bits {
            bit one {
                description "test";
            }

            bit "  two" {  // problem leading white space
                description "test description";
                status "current";
                reference "test reference";
                position "1";
            }
        }
    }
}
