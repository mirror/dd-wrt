module mod7 {
    prefix abc;
    namespace "urn:cesnet:mod7";

    typedef my {
        type bits {
            bit one {
                description "test";
            }

            bit "two  " {  // problem trailing white space
                description "test description";
                status "current";
                reference "test reference";
                position "1";
            }
        }
    }
}
