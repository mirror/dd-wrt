module mod2 {
    prefix abc;
    namespace "urn:cesnet:mod2";

    typedef my {
        type bits {
            bit one {
                description "test";
            }

            bit two {
                reference "test reference";
                description "test description";

                reference "test"; // duplicated
            }
        }
    }
}
