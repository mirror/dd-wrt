module mod11 {
    prefix abc;
    namespace "urn:cesnet:mod11";

    typedef my {
        type bits {
            bit one {
                description "test";
            }

            bit "two" {
                description "test description";
                status "current";
                reference "test reference";
                position "555";
            }

            bit three;

            bit four {
                position 4294967293;
            }

            bit five {
                position 555;
            }

            bit six {
                position 666;
            }

            bit seven;
            bit eight;
        }
    }
}
