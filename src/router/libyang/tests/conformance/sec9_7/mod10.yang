module mod10 {
    prefix abc;
    namespace "urn:cesnet:mod10";

    typedef my {
        type bits {
            bit one {
                description "test";
            }

            bit "two" {
                description "test description";
                status "current";
                reference "test reference";
                position "555";
            }

            bit three;

            bit four {
                position 4294967293;  // value is bigger than 4294967295
            }

            bit five;

            bit six {
                position 666;
            }

            bit seven;
            bit eight;
        }
    }
}
