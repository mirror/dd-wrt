module mod8 {
    prefix abc;
    namespace "urn:cesnet:mod8";

    typedef my {
        type bits {
            bit one {
                description "test";
            }

            bit "two" {
                description "test description";
                status "current";
                reference "test reference";
                position "-1";          // value is smaller than 0
            }
        }
    }
}
