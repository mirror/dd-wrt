module mod9 {
    prefix abc;
    namespace "urn:cesnet:mod9";

    typedef my {
        type bits {
            bit one {
                description "test";
            }

            bit "two" {
                description "test description";
                status "current";
                reference "test reference";
                position "1";
            }

            bit three;

            bit four {
                position "4294967296";  // value is bigger than 4294967295
            }
        }
    }
}
