module mod3 {
    prefix abc;
    namespace "urn:cesnet:mod3";

    identity i1 {
        reference "test reference";
        status current;
        description "test description";

        status obsolete; // duplicated
    }
}
