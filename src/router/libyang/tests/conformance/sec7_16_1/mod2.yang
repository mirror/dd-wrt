module mod2 {
    prefix abc;
    namespace "urn:cesnet:mod2";

    identity i1 {
        reference "test reference";
        description "test description";

        reference "test"; // duplicated
    }
}
