module mod5 {
    prefix abc;
    namespace "urn:cesnet:mod5";

    identity i1 {
        reference "test reference";
        status current;
        description "test description";

        base i2;
    }

    identity i3 {
        base i1;

        description "test identity3";
    }

    identity i2;

    leaf leaf {
        type identityref {
            base i2;
        }
    }

    identity i5 {
        status current;
        description "test1";
        reference "test2";
        base i3;
    }
}
