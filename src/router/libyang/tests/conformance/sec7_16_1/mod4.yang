module mod4 {
    prefix abc;
    namespace "urn:cesnet:mod4";

    identity i1 {
        reference "test reference";
        status current;
        base i2;
        description "test description";

        base i3; // duplicated
    }

    identity i2 {
        reference "test";
    }

    identity i3 {
        description test;
    }
}
