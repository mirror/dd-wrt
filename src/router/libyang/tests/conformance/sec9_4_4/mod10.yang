module mod10 {
    prefix abc;
    namespace "urn:cesnet:mod10";

    typedef my2 {
        type my {
            length "1..52" {
                reference "test reference";
                error-app-tag "test tag";
                description "test description";
                error-message "test error message";
            }
        }
    }

    typedef my {
        type string;
    }

    leaf leaf1 {
        type my;
    }

    leaf-list llist {
        type my2 {
            length "min..7 | 10 | 15 .. 25 | 26 .. max";
        }
    }

    leaf leaf3 {
        type my {
            length "min .. max";
        }
    }
}
