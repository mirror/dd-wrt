module mod8 {
    prefix abc;
    namespace "urn:cesnet:mod8";

    typedef my {
        type string {
            length "1..255";
        }
    }

    leaf leaf {
        type my {
            length "min .. 10 | 10 .. 25 | 27 .. max";
        }
    }
}
