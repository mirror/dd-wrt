module mod7 {
    prefix abc;
    namespace "urn:cesnet:mod7";

    typedef my-base-str-type {
         type string {
             length "1..255";
         }
     }

    leaf leaf1 {
        type my-base-str-type {
            // legal length refinement
            length "42..max | 11"; // wrong order
        }
    }
}
