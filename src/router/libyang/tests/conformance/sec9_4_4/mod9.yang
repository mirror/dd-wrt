module mod9 {
    prefix abc;
    namespace "urn:cesnet:mod9";

    typedef my {
        type string {
            length "1..255";
        }
    }

    leaf leaf {
        type string {
            length "min .. 25 | 10 .. 26 | 27 .. max";
        }
    }
}
