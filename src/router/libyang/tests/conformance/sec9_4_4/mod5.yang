module mod5 {
    prefix abc;
    namespace "urn:cesnet:mod5";

    typedef my-base-str-type {
         type string {
             length "1..255";
         }
     }

    leaf leaf1 {
        type my-base-str-type {
            // legal length refinement
            length "11 | 42..max"; // 11 | 42..255
        }
    }

    leaf leaf2 {
        type my-base-str-type {
            // illegal length refinement
            length "1..999";
        }
    }
}
