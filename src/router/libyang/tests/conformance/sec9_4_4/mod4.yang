module mod4 {
    prefix abc;
    namespace "urn:cesnet:mod4";

    typedef my {
        type string {
            length "1..255" {
                reference "test reference";
                error-app-tag "test tag";
                description "test description";
                error-message "test error message";

                error-message "test"; // duplicated
            }
        }
    }
}
