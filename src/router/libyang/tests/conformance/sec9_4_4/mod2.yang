module mod2 {
    prefix abc;
    namespace "urn:cesnet:mod2";

    typedef my {
        type string {
            length 1..255 {
                reference "test reference";
                description "test description";

                reference "test"; // duplicated
            }
        }
    }
}
