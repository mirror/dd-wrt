module mod1 {
    prefix abc;
    namespace "urn:cesnet:mod1";

    typedef my {
        type string {
            length "1 .. 255" {
                description "test description";

                description "test"; // duplicated
            }
        }
    }
}
