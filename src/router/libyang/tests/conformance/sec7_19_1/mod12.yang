module mod12 {
    namespace "urn:cesnet:mod12";
    prefix abc;

    grouping login {
        container login {
            config true;
            leaf user {
                type string;
            }

            leaf password {
                config true;
                type string;
            }
        }
    }

    notification test {

        container presence {
            config false;           // ignore config
            presence "enable";
            list list {
                key keys;

                leaf keys { type string; }

                leaf leaf {
                    type empty;
                }
            }
            uses login;
        }
    }
}
