module mod3 {
    namespace "urn:cesnet:mod3";
    prefix abc;

    grouping login {
        container login {
            leaf user {
                type string;
            }

            leaf password {
                config true;
                type string;
            }
        }
    }

    container ccc {
        container presence {
            presence "enable";
            list list {
                key keys;

                leaf keys { type string; }

                leaf leaf {
                    type empty;
                }
            }
            uses login;
        }

        config true;

        choice ch1 {

            case ca {
                container ssh {
                    presence "enable";
                    config true;        // problem with config true
                }
            }

            leaf-list ll {
                type uint8;
            }

            config false;
        }
    }
}
