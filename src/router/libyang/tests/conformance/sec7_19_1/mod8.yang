module mod8 {
    namespace "urn:cesnet:mod8";
    prefix abc;

    grouping login {
        container login {
            config true;
            leaf user {
                type string;
            }

            leaf password {
                config true;
                type string;
            }
        }
    }

    rpc test {
        output {
            container presence {
                config false;           // ignore config
                presence "enable";
                list list {
                    key keys;

                    leaf keys { type string; }

                    leaf leaf {
                        type empty;
                    }
                }
                uses login;
            }
        }
    }
}
