module mod9 {
    namespace "urn:cesnet:mod9";
    prefix abc;

    rpc test {
        output {
            grouping login {
                container login {
                    config false;       // ignore config
                    leaf user {
                        type string;
                    }

                    leaf password {
                        config true;    // ignore config
                        type string;
                    }
                }
            }

            container presence {
                config false;           // ignore config
                presence "enable";
                list list {
                    key keys;

                    leaf keys { type string; }

                    leaf leaf {
                        type empty;
                    }
                }
                uses login;
            }
        }
    }
}
