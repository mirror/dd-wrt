module mod5 {
    namespace "urn:cesnet:mod5";
    prefix abc;

    rpc test {
        input {
            grouping login {
                container login {
                    config false;
                    leaf user {
                        type string;
                    }

                    leaf password {
                        config true;  // ignore config
                        type string;
                    }
                }
            }

            container presence {
                config false;        // ignore config
                presence "enable";
                list list {
                    key keys;

                    leaf keys { type string; }

                    leaf leaf {
                        type empty;
                    }
                }
                uses login;
            }
        }
    }
}
