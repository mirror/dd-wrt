module mod10 {
    namespace "urn:cesnet:mod10";
    prefix abc;

    rpc test {
        output {
            grouping login {
                container login {
                    config true;        // ignore config
                    leaf user {
                        type string;
                    }

                    leaf password {
                        config true;    // ignore config
                        type string;
                    }
                }
            }

            container presence {
                config false;           // ignore config
                presence "enable";
                list list {
                    key keys;

                    leaf keys { type string; }

                    leaf leaf {
                        type empty;
                    }
                }
                uses login {
                    augment "login" {
                        leaf test {
                            config true;    // ignore config
                            type empty;
                        }
                    }
                }
            }
        }
    }

    augment "/test/output/presence" {
        leaf test {
            config true;                // ignore config
            type empty;
        }
    }
}
