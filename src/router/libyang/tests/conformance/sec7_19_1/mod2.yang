module mod2 {
    namespace "urn:cesnet:mod2";
    prefix abc;

    container ccc {
        config false;
        container presence {
            presence "enable";
            list list {
                key keys;

                leaf keys { type string; }

                leaf leaf {
                    type empty;
                }

                uses login;
            }
        }
    }

    grouping login {
        container login {
            config true;         // problem with config true
            leaf user {
                type string;
            }

            leaf password {
                config true;
                type string;
            }
        }
    }
}
