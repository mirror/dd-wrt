module mod1 {
    namespace "urn:cesnet:mod1";
    prefix abc;

    container ccc {
        config false;
        container presence {
            presence "enable";
            list list {
                key keys;

                leaf keys { type string; }

                leaf leaf {
                    type empty;
                    config true;    // problem with config true
                }
            }
        }
    }
}
