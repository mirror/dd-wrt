module mod7 {
    namespace "urn:cesnet:mod7";
    prefix abc;

    rpc test {
        input {
            container presence {
                container login {
                    config true;        // ignore config
                    leaf user {
                        type string;
                    }

                    leaf password {
                        config true;    // ignore config
                        type string;
                    }
                }

                config false;           // ignore config
                presence "enable";
                list list {
                    key keys;

                    leaf keys { type string; }

                    leaf leaf {
                        type empty;
                    }
                }
            }
        }
    }
}
