module mod1 {

    prefix abc;
    namespace "urn:cesnet:mod1";

    container cc {
        description "Test container";

        config true;

        container c {
            config false;
            description "Test container";

        }

        list ll {
            leaf aa {
                type uint8;
            }
            key "aa";

            container ccc;

            container abc {
                config false;
            }
        }
        config false; // duplicated config statement
    }
}
