module mod4  {

    prefix abc;
    namespace "urn:cesnet:mod4";

    reference "test module";

    container cc {
        description "Test container";
        reference "Test reference";

        config true;

        container c {
            config false;
            description "Test container";

        }

        presence "aaa";

        list ll {
            leaf aa {
                type uint8;
                reference "test leaf";
            }
            key "aa";

            reference "test list";

            container ccc;

            container abc {
                config false;
                reference "avc";
                presence "test2";
            }
        }
        presence "test"; // duplicated presence statement
    }
}
