module mod2 {

    prefix abc;
    namespace "urn:cesnet:mod2";

    container cc {
        description "Test container";

        config true;

        container c {
            config false;
            description "Test container";

        }

        list ll {
            leaf aa {
                type uint8;
            }
            key "aa";

            container ccc;

            container abc {
                config false;
            }
        }
        description false; // duplicated description statement
    }
}
