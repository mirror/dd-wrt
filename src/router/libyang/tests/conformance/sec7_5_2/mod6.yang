module mod6 {

    prefix abc;
    namespace "urn:cesnet:mod6";

    reference "test module";

    container cc {
        description "Test container";
        reference "Test reference";

        config true;

        container c {
            config false;
            description "Test container";
        }
        status "obsolete";
        presence "aaa";

        when "../confirm-event = 'start' or ../confirm-event = 'extend'";

        list ll {
            leaf aa {
                type uint8;
                reference "test leaf";
            }
            key "aa";

            reference "test list";

            container ccc;

            container abc {
                config false;
                reference "avc";
                presence "test2";
            }
        }

        when "../confirm-event = 'start' or ../confirm-event = 'extend'";
    }

    leaf confirm-event {
        type enumeration {
            enum start;
            enum extend;
            enum stop;
            enum "basic";
        }
    }
}
