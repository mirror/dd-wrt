module mod3 {

    prefix abc;
    namespace "urn:cesnet:mod3";

    reference "test module";

    container cc {
        description "Test container";
        reference "Test reference";

        config true;

        container c {
            config false;
            description "Test container";

        }

        list ll {
            leaf aa {
                type uint8;
                reference "test leaf";
            }
            key "aa";

            reference "test list";

            container ccc;

            container abc {
                config false;
                reference "avc";
            }
        }
        reference "test"; // duplicated reference statement
    }
}
