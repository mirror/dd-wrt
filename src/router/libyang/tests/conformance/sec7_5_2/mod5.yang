module mod5  {

    prefix abc;
    namespace "urn:cesnet:mod5";

    reference "test module";

    container cc {
        description "Test container";
        reference "Test reference";

        config true;

        container c {
            config false;
            description "Test container";
        }
        status "obsolete";
        presence "aaa";

        list ll {
            leaf aa {
                type uint8;
                reference "test leaf";
            }
            key "aa";

            reference "test list";

            container ccc;

            container abc {
                config false;
                reference "avc";
                presence "test2";
            }
        }
        status current; // duplicated presence statement
    }
}
