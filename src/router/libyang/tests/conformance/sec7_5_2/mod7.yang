module mod7 {

    prefix mod;
    namespace "urn:cesnet:mod7";

    feature f1 {
        description "OK";
    }

    feature f2;

    container cont1 {
        presence "Test presence container";

        container ccc;

        anyxml any;

        leaf ifType {
             type enumeration {
                 enum ethernet;
                 enum atm;
             }
         }

         leaf ifMTU {
             type uint32;
         }

         must "ifType != 'ethernet' or " +
              "(ifType = 'ethernet' and ifMTU = 1500)" {
             error-message "An ethernet MTU must be 1500";
         }


        grouping ggg {
            description "test";

            leaf abc {
                type int32;
            }
        }

        choice ch {
            container cc {
                leaf aa {
                    type string;
                }

                leaf bb {
                    type empty;
                }

                container state {
                    config false;
                    status current;

                    description "test config";
                    reference "test reference config";

                }

                container gg {
                    if-feature f1;


                    uses g;

                    description "aaa";

                    uses ggg;

                    list list1 {
                        key "aa";

                        leaf aa {
                            type leafref {
                                path "../../../bb";
                            }
                        }
                    }

                    list list2 {
                        key "bb";

                        leaf bb {
                            type string;
                        }
                    }

                    if-feature f2;
                    when "/cc_when/test = 1";
                }
            }
        }

        anyxml anyxml2;

        grouping g {
            container g {
                typedef test {
                    type uint8 {
                        range "1 .. 11 | 100..max";
                    }
                }

                leaf-list ll1 {
                    type test;
                }

                leaf-list ll2 {
                    type string;
                }
            }
        }

        leaf l1 {
            type decimal64 {
                fraction-digits 3;
            }
        }

        choice ch256 {
            case c1 {
                leaf abc {type string;}
            }

            case c2 {
                leaf abc2 {type int32;}
            }
        }

        must "ifType != 'atm' or " +
              "(ifType = 'atm' and ifMTU <= 17966 and ifMTU >= 64)" {
             error-message "An atm MTU must be  64 .. 17966";
         }

    }

    container cc_when {
        leaf test {
            type uint8;
        }
    }

}
