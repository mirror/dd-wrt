module mod7 {
    
    prefix abc;
    namespace "http://www.example.com";

    revision 2008-01-01 {
        description "This modul is imported.";
    }
    
    grouping a {
        leaf eh {
            type string {
                pattern '[A-Z]+';
                length 255;
            }
        }
    }
}
