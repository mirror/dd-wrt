module mod2 {
    prefix abc;
    namespace "urn:cesnet:mod2";

    grouping ssh {
        container ssh {
            leaf key { type string; }
            leaf user {
                type string {
                    pattern '[a-z0-9]';
                }
            }
            leaf is_valid {
                type boolean;
                default "false";
            }
        }
    }

    container server {
        uses ssh {
            refine ssh/is_valid {
                description "test";
                default atrue;      // bad boolean value
            }
        }
    }
}
