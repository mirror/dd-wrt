module mod3 {
    prefix abc;
    namespace "urn:cesnet:mod3";

    grouping ssh {
        container ssh {
            leaf key { type string; }
            leaf user {
                type string {
                    pattern '[a-z0-9]';
                }
            }
            leaf is_valid {
                type boolean;
                default "false";
            }
        }

        choice ch1 {
            case ca {
                container presence {
                    presence "enable";
                }
            }

            leaf str { type string; }
        }
    }

    container server {
        uses ssh {
            refine ch1 {
                description "test";
                default string;     // nothing case string
            }
        }
    }
}
