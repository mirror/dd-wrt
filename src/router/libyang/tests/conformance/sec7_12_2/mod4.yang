module mod4 {
    prefix abc;
    namespace "urn:cesnet:mod4";

    grouping ssh {
        container ssh {
            leaf key { type string; }
            leaf user {
                type string {
                    pattern '[a-z0-9]';
                }
            }
            leaf is_valid {
                type boolean;
                default "false";
            }
        }

        choice ch1 {
            case ca {
                container presence {
                    presence "enable";
                }
            }

            leaf str { type string; }
        }
    }

    container server {
        uses ssh {
            refine ssh {
                description "test";
                default string;     // bad statement
            }
        }
    }
}
