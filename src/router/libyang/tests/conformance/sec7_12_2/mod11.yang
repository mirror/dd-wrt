module mod11 {
    prefix abc;
    namespace "urn:cesnet:mod11";

    grouping ssh {
        container ssh {
            config false;
            leaf key { type string; }
            leaf user {
                type string {
                    pattern '[a-z0-9]';
                }
            }
            leaf is_valid {
                type boolean;
                default "false";
            }

            leaf-list test {
                type string;
                max-elements 7;
            }
        }

        choice ch1 {
            case ca {
                container presence {
                    presence "enable";
                }
            }

            leaf str { type string; }
        }

        choice test {
            case ll {
                container ccc {
                    container cc {
                        leaf mandatory {
                            type uint8;
                        }
                    }
                }
            }

            container presence2 {
                presence "enable";
            }

            default ll;
        }
    }

    container server {
        uses ssh {
            refine "ssh/test" {
                reference "test";
                min-elements 10; // min-elements is bigger than max-elements
            }
        }
    }
}
