module mod6 {
    prefix abc;
    namespace "urn:cesnet:mod6";

    grouping ssh {
        container ssh {
            config false;
            leaf key { type string; }
            leaf user {
                type string {
                    pattern '[a-z0-9]';
                }
            }
            leaf is_valid {
                type boolean;
                default "false";
            }
        }

        choice ch1 {
            case ca {
                container presence {
                    presence "enable";
                }
            }

            leaf str { type string; }
        }
    }

    container server {
        uses ssh {
            refine ssh/user {
                reference "test";
                presence true;  // bad target node
            }
        }
    }
}
