module mod4 {
	
	prefix abc;
	namespace "urn:cesnet:mod4";

	import mod_2 {
		prefix m1;
		revision-date "2016-06-30";
	}

	import mod_2 {
		prefix m2;
		revision-date "2016-07-12";
	}

	// multilple revision of module
}
