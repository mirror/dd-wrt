module mod_2 {
	
	namespace "urn:cesnet:mod_3";
	prefix cesnet;

	revision 2016-07-12 {
		description "test";
		reference "test1";
	};

	revision 2016-06-30 {
		reference "test";
		description "test1";
	};

	identity i2;

	identity i6 {
		description "test";
	}


}
