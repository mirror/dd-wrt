module mod5 {
	
	
    namespace "urn:cesnet:mod5";
	
    yang-version "1";

    prefix m;


	include sub5_1 {
		revision-date "2016-09-09";
	}

	include sub5_1 {
        revision-date 2016-08-08;
    }

    // multilple revision of submodule

}
