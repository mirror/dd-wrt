module mod6 {
	
	yang-version "1";
    namespace "urn:cesnet:mod6";
	prefix mmm;

    import mod_1 {
		prefix m;
		revision-date "2016-09-09";
	}

    include "sub6";

    import mod_3 {
        prefix t;
    }

	organization "ACME Inc.";
    contact
        "Joe L. User

         ACME, Inc.
         42 Anywhere Drive
         Nowhere, CA 95134
         USA

         Phone: +1 800 555 0100
         EMail: joe@acme.example.com";

    reference      "Test reference.";

    description
        "The module for entities implementing the ACME protocol.";

    leaf name {
        type t:hostname;
        default "Computer99";
    }
}
