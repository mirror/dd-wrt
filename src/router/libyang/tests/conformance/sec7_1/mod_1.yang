module mod_1 {
	
	namespace "urn:cesnet:mod_1";
	prefix cesnet;

	yang-version 1;

	revision 2016-09-09 {
		reference text;
	}

	revision 2016-08-08 {
		description "leaf { type string; }";
	}

	grouping mod {
		container mccc {
			typedef abc {
				type string {
					pattern '[a-zA-Z]+[0-9]*';
				}
			}

			leaf aa {
				type abc;
			}
		}
	}

	typedef mod_aa {
		type enumeration {
			enum aaa;
			enum bbb;
			enum ccc;
		}
	}
}
