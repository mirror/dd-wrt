module mod {

    prefix abc;
    namespace "http://www.google.sk";

    typedef hostname {
        type string {
            length "0..255";
        }
    }

    container hide {
        typedef hide_hostname {
            type string {
                length "0..128";
            }
        }
    }

    grouping g {

        leaf a {
            type uint8;
        }

        leaf b {
            type string;
        }
    }

    container c {

        grouping gg {

            leaf c {
                type hostname;
            }
        }
    }
}
