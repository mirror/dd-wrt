module mod7 {

    prefix abc;
    namespace "http://www.example.com";

    import mod {
      prefix sk;
    }

    grouping h {

        leaf abc {
            type sk:hostname;
        }

    }

    container hide {
        typedef hide_hostname {
            type string {
                length "0..128";
            }
        }

        list b {
            grouping g {
                leaf test1 {
                    type sk:hostname;
                }

                grouping gg1 {    
                    leaf test2 {
                        type hide_hostname;
                    }
                    uses h;
                }

                grouping gg2 {
                    leaf test3 {
                        type name;
                    }
                }


            }

            leaf test4 {
                type uint8;
            }
            
            typedef name {
                type string {
                    length "0..128";
                }
            }
            config false;

            uses sk:g;
        }
    }
}
