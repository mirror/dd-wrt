module mod3 {

    prefix abc;
    namespace "http://www.google.sk";

    typedef hostname {
        type string {
            length "0..255";
        }
    }

    container hide {
        typedef hide_hostname {
            type string {
                length "0..128";
            }
        }

        list b {
            config "false";
            typedef hostname {
                type string {
                    length "0..128";
                }
            }
        }
    }
}
