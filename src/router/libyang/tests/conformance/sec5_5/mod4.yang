module mod4 {

    prefix abc;
    namespace "http://www.example.sk";

    typedef hostname {
        type string {
            length "0..255";
        }
    }

    container hide {
        typedef hide_hostname {
            type string {
                length "0..128";
            }
        }

        list b {
            key aa;

            leaf aa {
                type hostname;
                default "aaa";
            }

            typedef hide_hostname {
                type string {
                    length "0..128";
                }
            }
        }
    }
}
