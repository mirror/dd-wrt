module mod5 {

    namespace "http://www.example.com";
    prefix abc;

    grouping g {
        typedef name {
            type string;
        }
    }

    container c {
        grouping g {
            leaf test {
                type decimal64 {
                    fraction-digits 1;
                }
            }
        }
    }
}
