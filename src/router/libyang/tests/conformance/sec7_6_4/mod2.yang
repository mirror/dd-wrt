module mod2 {

    prefix abc;
    namespace "urn:cesnet:mod2";

    container ccc {
        typedef my {
            type string {
                length "1..8";
            }
            description test;
        }

        leaf leaf1 {
            type my;
            default "passwords";
        }
    }
}
