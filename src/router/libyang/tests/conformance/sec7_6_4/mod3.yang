module mod3 {

    prefix abc;
    namespace "urn:cesnet:mod3";

    container ccc {
        typedef my {
            type string {
                length "1..8";
            }
            description test;
        }

        leaf leaf1 {
            type my;
            default "password";
        }

        leaf leaf2 {
            type default;
        }

        leaf leaf3 {
            type default;
            default "user";
        }
    }

    leaf test {
        type boolean;
        default true;
    }

    typedef default {
        type string {
            pattern '[a-zA-Z]+';
            length "1..25";
        }
        default Admin;
    }

    container cc {
        container presence {
            leaf leaf4 {
                default "hostname";
                type string {
                    pattern "[a-z]+";
                }
            }

            presence "enable";
        }
    }
}
