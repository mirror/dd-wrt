module mod3 {
    prefix abc;
    namespace "urn:cesnet:mod3";

    container cont {
        list ll {
            key kk;

            leaf kk { type int32; }

            unique "list/test test";

            leaf test { type string; }

            list list {
                key key;

                leaf key { type int8; }

                leaf test { type string; }
            }
        }
    }
}
