module mod1 {
    namespace "urn:cesnet:mod1";
    prefix abc;

    list ll {
        key k;

        leaf k { type uint8; }

        unique "ff/cc";

        container ff {
            leaf-list cc {
                type string;
            }
        }
    }
}
