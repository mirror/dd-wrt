module mod2 {
    prefix abc;
    namespace "urn:cesnet:mod2";

    leaf kk {
        type string;
    }

    container ccc {
        list ll {
            key keys;

            leaf keys { type int16; }

            unique "config cont/state";

            leaf config { type boolean; }

            container cont {
                leaf state {
                    type string {
                        pattern '[a-z]+';
                    }
                    config false;
                }
            }
        }
    }
}
