module mod5 {
    prefix abc;
    namespace "urn:cesnet:mod5";

    list ll {
        key k;

        leaf k {
            type enumeration {
                enum a1;
                enum a2 {
                    value "5";
                }
                enum a3;
            }
        }

        unique "test";
        unique "cont/test";

        leaf test {
            type int8;
            config false;
        }

        container cont {
            leaf test {
                type string;
                config true;
            }
        }
    }
}
