module mod4 {
    prefix abc;
    namespace "urn:cesnet:mod4";

    leaf kk {
        type string;
    }

    container ccc {
        list ll {
            key keys;

            leaf keys { type int16; }

            unique "config cont/config dup_config";

            leaf config { type boolean; }

            container cont {
                leaf config {
                    type string {
                        pattern '[a-z]+';
                    }
                    config true;
                    default "ok";
                }
            }

            leaf dup_config {
                type string {
                    pattern '[a-z]+';
                }
                default "ok";
            }
        }
    }

    container presence {
        presence "enable";

        list ll {
            leaf keys { type int16; }

            key keys;

            unique "test";
            unique "cont/test";

            leaf test {
                type string;
                default "name";
            }

            container cont {

                leaf test {
                    type string;
                    default "name";
                }
            }
        }
    }

    list server {
        key "name";
        unique "ip port";
        leaf name {
            type string;
        }
        leaf ip {
            type string {
                pattern '[0-9\.]*';
            }
        }
        leaf port {
            type uint16;
        }
    }
}
