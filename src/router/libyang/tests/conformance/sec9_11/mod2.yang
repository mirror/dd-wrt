module mod2 {
    prefix abc;
    namespace "urn:cesnet:mod2";

    typedef my {
        type empty;
    }

    leaf leaf {
        type my2 {
            default "";   // empty type cannot have default value
        }
    }

    typedef my2 {
        type my;
    }
}
