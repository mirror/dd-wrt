module mod3 {
    prefix abc;
    namespace "urn:cesnet:mod3";

    typedef my {
        type empty;
    }

    leaf leaf {
        type my2 {
            default 0;   // empty type cannot have default value
        }
    }

    typedef my2 {
        type my;
    }
}
