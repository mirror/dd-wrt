module mod1 {
    prefix abc;
    namespace "urn:cesnet:mod1";

    typedef my_type {
        type string {
            pattern '[a-z]+';
        }
        status deprecated;
    }

    container ccc {
        leaf my {
            status current;
            type my_type; // illegal, since my-type is deprecated
        }
    }
}
