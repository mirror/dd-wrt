module mod {
    prefix m;
    namespace "urn:cesnet:mod";

    grouping login {
        status obsolete;

        container login {
            leaf username {
                type string;
            }

            leaf password {
                type string {
                    length "6..64";
                }
            }
        }
    }
}
