module mod6 {
    prefix abc;
    namespace "urn:cesnet:mod6";

    list list {
        key "key1 key2";

        leaf-list key1 {
            type int8;
        }

        leaf key2 {
            type string;
            status "obsolete";
        }

        leaf port {
            type uint16;
        }
    }
}
