submodule sub5 {
    belongs-to mod5 {
        prefix m;
    }

    grouping login {
        status obsolete;

        container login {
            leaf username {
                type string;
            }

            leaf password {
                type string {
                    length "6..64";
                }
            }
        }
    }
}
