module mod3 {
    prefix abc;
    namespace "urn:cesnet:mod3";

    identity i2 {
        base i1;
        status obsolete;
    }

    identity i1 {
        status "obsolete";
    }

    leaf leaf {
        type identityref {
            base i2;
        }
    }
}
