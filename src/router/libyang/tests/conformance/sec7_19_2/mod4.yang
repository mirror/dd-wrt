module mod4 {
    prefix abc;
    namespace "urn:cesnet:mod4";

    feature f2 {
        if-feature f3;
    }

    feature f3;

    feature f1 {
        status obsolete;
        if-feature f2;
    }

    feature f4 {
        if-feature f1;
        status deprecated;
    }
}
