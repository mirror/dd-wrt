module mod9 {
    prefix abc;
    namespace "urn:cesnet:mod9";

    include sub9;

    import mod {
        prefix mod;
    }

    container abc {
        leaf test {
            type my;
        }
        if-feature f1;
        status obsolete;
    }

    identity i4 {
        base i3;
        status obsolete;
    }

    leaf test {
        type identityref {
            base i3;
        }
        status deprecated;
    }

    typedef my {
        type boolean;
        status current;
    }

    uses gg {
        status deprecated;
    }

    list list {
        key keys;
        unique leaf;

        leaf keys {
            status current;
            type int16;
        }

        leaf leaf {
            status current;
            type string;
        }

        leaf ref {
            type leafref {
                path "../../target";
            }
            status obsolete;
        }

    }

    leaf target {
        status deprecated;
        type boolean;
    }

    uses mod:login {
        status current;
    }
}
