submodule sub9 {
    belongs-to mod9 {
        prefix mod;
    }

    feature f1 {
        status obsolete;
    }

    feature f2 {
        description "test";
    }

    identity i3 {
        status deprecated;
    }

    identity i2 {
        base i3;
        status deprecated;
    }

    grouping gg {
        status deprecated;
        container connect {
            leaf ip {
                type string {
                    pattern '[0-9]+\.[0-9]+\.[0-9]+\.[0-9]+';
                    length "7..15";
                }
            }

            leaf port {
                type uint16;
            }
        }
    }
}
