module mod1 {
    prefix abc;
    namespace "urn:cesnet:mod1";

    grouping gr {
        leaf l1 { type my; }

        typedef my {
            type string {
                pattern '[a-zA-Z]+';
                pattern 'host-.*';
                length "8..255";
            }
            description "test";
        }

        container presence {
            presence "enable";
        }
    }

    container ccc {
        uses gr {
            description "test description";

            description "test"; // duplicated
        }
    }
}
