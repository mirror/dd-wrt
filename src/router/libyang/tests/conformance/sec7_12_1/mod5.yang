module mod5 {
    prefix abc;
    namespace "urn:cesnet:mod5";

    feature f1;

    grouping gr {
        leaf l1 { type my; }

        typedef my {
            type string {
                pattern '[a-zA-Z\-]+';
                pattern 'host-.*';
                length "8..255";
            }
            description "test";
        }

        container presence {
            presence "enable";
        }
    }

    feature f2;

    container ccc {
        uses gr {
            when '../leaf';
            if-feature f2;
            reference "test reference";
            status "current";
            description "test description";

            if-feature f1;
        }
    }

    leaf leaf { type int16; }
}
