module mod4 {
    prefix abc;
    namespace "urn:cesnet:mod4";

    grouping gr {
        leaf l1 { type my; }

        typedef my {
            type string {
                pattern '[a-zA-Z]+';
                pattern 'host-.*';
                length "8..255";
            }
            description "test";
        }

        container presence {
            presence "enable";
        }
    }

    container ccc {
        uses gr {
            when '../leaf';
            reference "test reference";
            status "current";
            description "test description";

            when '../leaf'; // duplicated
        }

        leaf leaf { type int16; }
    }
}
