module mod3 {
    prefix abc;
    namespace "urn:cesnet:mod3";

    grouping gr {
        leaf l1 { type my; }

        typedef my {
            type string {
                pattern '[a-zA-Z]+';
                pattern 'host-.*';
                length "8..255";
            }
            description "test";
        }

        container presence {
            presence "enable";
        }
    }

    container ccc {
        uses gr {
            reference "test reference";
            status "deprecated";
            description "test description";

            status current; // duplicated
        }
    }
}
