module mod {
    prefix m;
    namespace "urn:cesnet:mod";

    grouping gr {
        container login {
            leaf username { type t_log; }

            leaf password {
                type string {
                    length "8..255";
                }
            }
        }
    }

    typedef t_log {
        type string {
            pattern '[a-zA-Z][a-zA-Z0-9_]*';
            length "6..255";
        }
    }
}
