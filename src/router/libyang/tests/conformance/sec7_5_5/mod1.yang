module mod1 {
    prefix abc;
    namespace "urn:cesnet:mod1";

    container test {
        leaf test {
            type string;
        }

        leaf-list list {
            type uint8;
        }
    }

    container presence {
        presence "Test1";

        uses login;
    }

    grouping login {
        list login {
            key "user";

            leaf user {
                type string {
                    pattern "[a-zA-Z]+";
                }
            }

            leaf password {
                type string {
                    length "6..255";
                }
            }
        }
    }
}
