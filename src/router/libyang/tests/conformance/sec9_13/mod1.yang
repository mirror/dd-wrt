module mod1 {
    prefix abc;
    namespace "urn:cesnet:mod1";

    typedef my {
        type instance-identifier {
            require-instance true;
            require-instance false; // duplicated
        }
    }
}
