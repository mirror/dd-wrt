module mod3 {
    prefix pref;
    namespace "urn:cesnet:mod3";

    typedef my_true {
        type instance-identifier {
            require-instance "true";
        }
    }

    container instance {
        leaf-list llist1 {
            type my_true;
        }

        leaf-list llist2 {
            type my_true {
                require-instance "false";
            }
        }
    }

    container cont {
        presence "enable";
        leaf l1 {
            type boolean;
        }
    }

    list list {
        key "key1 key2";

        leaf key1 {
            type string;
        }

        leaf key2 {
            type uint8;
        }

        leaf port {
            type uint16;
        }
    }

    container ccc {
        leaf-list llist {
            type enumeration {
                enum zero;
                enum one;
                enum two;
                enum unknown {
                    value -1;
                }
            }
        }

        list state {
            config false;

            leaf keys {
                type string;
            }

            container cont {
                leaf-list llist {
                    type int8;
                }
            }
        }

        list list {
            key keys;

            leaf keys {
                type string;
            }

            container cont {
                leaf-list llist {
                    type int8;
                }
            }
        }
    }
}
