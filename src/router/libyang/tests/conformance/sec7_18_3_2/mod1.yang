module mod1 {
    prefix abc;
    namespace "urn:cesnet:mod1";

    import mod {
        prefix mod;
    }

    deviation "/mod:lleaf" {
        description "test";

        deviate add {
            min-elements 2;
            default "leaf";
        }
    }
}
