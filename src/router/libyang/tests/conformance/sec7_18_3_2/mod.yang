module mod {
    prefix m;
    namespace "urn:cesnet:mod";

    grouping login {
        leaf user {
            type string {
                pattern '[A-Za-z]+';
            }
        }

        leaf password {
            type string {
                length "6..255";
            }
        }
    }

    container cont {
        uses login;
    }

    choice ch1 {
        case ca {
            leaf l1 { type uint8; }
        }

        leaf-list ll1 { type string; }
    }

    leaf-list lleaf { type int16; }

    container ccc {
        list list {
            key keys;

            unique "ip port";
            unique name;

            leaf keys { type string; }

            leaf ip {
                type string {
                    pattern '[0-9]+\.[0-9]+\.[0-9]+\.[0-9]+';
                }
            }

            leaf port { type uint16; }

            leaf name { type string; }

            leaf error { type uint8; }
        }

        leaf test { type empty; }
    }

    leaf default {
        type string;
        default "default";
    }

    leaf test1 {
        type boolean;
    }

}
