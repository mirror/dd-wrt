module mod9 {
    prefix abc;
    namespace "urn:cesnet:mod9";

    import mod {
        prefix mod;
    }

    deviation "/mod:default" {
        description "test";

        deviate delete {
            default "default";
        }

        deviate add {
            default "def";
            default "dd"; //duplicated
        }
    }
}
