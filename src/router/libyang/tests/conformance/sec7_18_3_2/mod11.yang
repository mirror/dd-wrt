module mod11 {
    prefix abc;
    namespace "urn:cesnet:mod11";

    import mod {
        prefix mod;
    }

    deviation "/mod:ccc/mod:list" {
        reference "test";

        deviate add {
            min-elements 2;
            min-elements 10; //duplicated
        }
    }
}
