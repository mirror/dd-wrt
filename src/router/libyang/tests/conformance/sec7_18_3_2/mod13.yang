module mod13 {
    prefix abc;
    namespace "urn:cesnet:mod13";

    import mod {
        prefix mod;
    }

    deviation "/mod:cont/mod:user" {
        deviate add {
            mandatory true;
        }
    }

    deviation "/mod:lleaf" {
        deviate add {
            max-elements 3;
            min-elements 1;
        }
    }

    deviation "/mod:default" {
        deviate delete {
            default "default";
        }
    }

    deviation "/mod:ccc/mod:test" {
        deviate add {
            must "../../default = 'my'";
        }
    }

    deviation "/mod:ccc/mod:test" {
        deviate replace {
            type my_type;
        }
    }

    deviation "/mod:test1" {
        deviate add {
            must "/ccc/test = 12";
        }
    }

    typedef my_type {
        type int16 {
            range "-50 .. 50";
        }

        default 12;
    }
}
