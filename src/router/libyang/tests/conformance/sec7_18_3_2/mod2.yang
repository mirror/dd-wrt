module mod2 {
    prefix abc;
    namespace "urn:cesnet:mod2";

    import mod {
        prefix mod;
    }

    deviation "/mod:lleaf" {
        description "test";

        deviate add {
            max-elements 2;
        }

        deviate add {
            min-elements 3;
        }
    }
}
