module mod12 {
    prefix abc;
    namespace "urn:cesnet:mod12";

    import mod {
        prefix mod;
    }

    deviation "/mod:default" {
        reference "test";

        deviate add {
            units "kilogram";
            units "kilobyte"; //duplicated
        }
    }
}
