module mod8 {
    prefix abc;
    namespace "urn:cesnet:mod8";

    import mod {
        prefix mod;
    }

    deviation "/mod:default" {
        description "test";

        deviate delete {
            default "default";
        }

        deviate add {
            config true;
            config false; //duplicated
        }
    }
}
