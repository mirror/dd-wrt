module mod10 {
    prefix abc;
    namespace "urn:cesnet:mod10";

    import mod {
        prefix mod;
    }

    deviation "/mod:ccc/mod:list" {
        description "test";

        deviate add {
            max-elements 2;
            max-elements 10; //duplicated
        }
    }
}
