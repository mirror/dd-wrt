module mod5 {
    prefix abc;
    namespace "urn:cesnet:mod5";

    import mod {
        prefix mod;
    }

    deviation "/mod:ccc/mod:list" {
        description "test";

        deviate add {
            unique "error";
        }

        deviate delete {
            unique "name ip";
        }
    }
}
