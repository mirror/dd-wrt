module mod7 {
    prefix abc;
    namespace "urn:cesnet:mod7";

    import mod {
        prefix mod;
    }

    deviation "/mod:default" {
        description "test";

        deviate delete {
            default "default";
        }

        deviate add {
            mandatory true;
            mandatory false; //duplicated
        }
    }
}
