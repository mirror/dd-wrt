module mod4 {
    prefix abc;
    namespace "urn:cesnet:mod4";

    import mod {
        prefix mod;
    }

    deviation "/mod:default" {
        description "test";

        deviate add {
            default "llist";
        }
    }
}
