module mod3 {

    prefix abc;
    namespace "urn:cesnet:mod3";

    leaf aa {
        config true;

        description "test description";

        reference reference;

        type string;

        config "false"; // duplicated
    }
}
