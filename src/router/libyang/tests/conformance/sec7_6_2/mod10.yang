module mod10 {

    prefix abc;
    namespace "urn:cesnet:mod10";

    container lll {

        leaf aa {
            config true;

            status "current";

            units "something";

            description "test description";

            when "../../abc = 8";

            reference " test reference";

            type string;

            default "dup";

            mandatory false;

            type string { // duplicated
                pattern "[a-zA-Z]+";
                pattern "xa.+";
                length "1..256";
            }
        }

    }

    leaf abc {
        type uint8;
    }

}
