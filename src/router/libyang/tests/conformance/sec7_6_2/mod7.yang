module mod7 {

    prefix abc;
    namespace "urn:cesnet:mod7";

    list lll {
        key bb;

        leaf aa {
            config true;

            status "current";

            units "something";

            description "test description";

            reference " test reference";

            type string;

            default "dup";

            mandatory false;

            units obsolete; // duplicated
        }

        leaf bb {
            type boolean;
        }
    }

}
