module mod9 {

    prefix abc;
    namespace "urn:cesnet:mod9";

    list lll {
        key bb;

        leaf aa {
            config true;

            status "current";

            units "something";

            description "test description";

            when "../../abc = 8";

            reference " test reference";

            // missing type

            default "dup";

            mandatory false;

        }

        leaf bb {
            type int16;
        }
    }

    leaf abc {
        type uint8;
    }
}
