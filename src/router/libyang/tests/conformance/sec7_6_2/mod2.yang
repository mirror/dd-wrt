module mod2 {

    prefix abc;
    namespace "urn:cesnet:mod2";

    leaf aa {

        type string;

        description "test description";

        reference " test reference";

        description "dup. description"; // duplicated
    }
}
