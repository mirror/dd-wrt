module mod4 {

    prefix abc;
    namespace "urn:cesnet:mod4";

    container ccc {
        leaf aa {
            config true;

            default "abc";

            description "test description";

            reference " test reference";

            type string;

            default "dup"; // duplicated
        }
    }
}
