module mod8 {

    prefix abc;
    namespace "urn:cesnet:mod8";

    container ccc {

        leaf aa {
            config true;

            status "current";

            units "something";

            description "test description";

            when "../../abc = 8";

            reference " test reference";

            type string;

            mandatory false;

            when "../../abc = 8"; // duplicated

        }
    }

    leaf abc {
        type uint8;
    }

}
