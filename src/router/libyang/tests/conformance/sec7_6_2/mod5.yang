module mod5 {

    prefix abc;
    namespace "urn:cesnet:mod5";

    container ccc {
        leaf aa {
            config true;

            mandatory "true";

            description "test description";

            reference " test reference";

            type string;

            mandatory false; // duplicated
        }
    }
}
