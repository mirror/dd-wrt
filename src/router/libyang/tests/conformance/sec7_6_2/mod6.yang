module mod6 {

    prefix abc;
    namespace "urn:cesnet:mod6";

    container ccc {
        leaf aa {
            config true;

            status "current";

            description "test description";

            reference " test reference";

            type string;

            default "dup";

            mandatory false;

            status obsolete; // duplicated
        }
    }
}
