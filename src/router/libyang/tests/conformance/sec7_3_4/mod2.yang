module mod2 {

    prefix abc;
    namespace "urn:cesnet:mod2";

    typedef name {
        type string;
        description "new type without restrictions";
    }

    typedef name2 {
        type name1 {
            pattern '[A-Ca-z]+';
            length "1..3";
        }
    }

    typedef name1 {
        type name {
            pattern '[a-zA-Z]+';
        }
        default 'XaBc';
    }

    container login {
        leaf login {
            type name {
                length "1..255";
            }
            default "abc";
        }

        leaf hostname {
            type name1;
        }
    }
}
