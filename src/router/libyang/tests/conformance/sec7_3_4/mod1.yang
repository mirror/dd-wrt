module mod1 {

    prefix abc;
    namespace "urn:cesnet:mod1";

    typedef name {
        type string;
        description "new type without restrictions";
    }

    typedef name1 {
        type string {
            pattern '[a-z]+';
        }
        default 'xabc';
    }

    container login {
        leaf login {
            type name {
                length "1..255";
            }
            default "abc";
        }

        leaf hostname {
            type name1 {
                length "1..3";
            }
        }
    }
}
