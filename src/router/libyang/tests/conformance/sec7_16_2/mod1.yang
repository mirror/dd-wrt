module mod1 {
    prefix abc;
    namespace "urn:cesnet:mod1";

    import mod {
        prefix mod;
    }

    include sub1;

    identity i1 {
        description "test";
        base abc:i2;
    }

    identity i2;

    identity i3 {
        base mod:i2;
    }

    identity i4 {
        base sub_i4;
    }

    identity i5 {
        base sub_i5;
    }
}
