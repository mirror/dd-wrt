module mod4 {
    prefix abb;
    namespace "urn:cesnet:mod4";

    identity i1 {
        description "test";
        base i2;
    }

    identity i4 {
        base i1;   // reference itself indirectly
    }

    identity i3 {
        base i5;
    }

    identity i2 {
        base i3;
    }

    identity i5 {
        base i4;
    }
}
