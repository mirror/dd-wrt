module mod {
    prefix m;
    namespace "urn:cesnet:mod";

    identity i1 {
        status obsolete;
    }

    identity i2 {
        base m:i3;
    }

    identity i3 {
        description "test";
        reference "test";
    }

    identity j3 {
        base m:j2;
    }

    identity j2;
}
