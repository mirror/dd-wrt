module mod2 {
    prefix abc;
    namespace "urn:cesnet:mod2";

    typedef my {
        type union {
            type uint8;
            type string;
            type empty;   // not allow empty in union
        }
    }
}
