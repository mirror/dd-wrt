module mod4 {
    prefix abc;
    namespace "urn:cesnet:mod4";

    typedef my {
        type union {
            type my_num {
                range "min..-100 | -50 .. 50 | 100..max";
            }
            type uint8;
            type enumeration {
                enum unknown {
                    value -1000;
                }

                enum zero {
                    value 0;
                }

                enum one;
            }
            type string {
                length "1..255";
                pattern '[a-zA-Z]+';
                pattern 'aaa.+' {
                    description "test";
                    description "test"; // duplicated
                }
            }
        }
    }
}
