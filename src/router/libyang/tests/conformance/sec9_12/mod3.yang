module mod3 {
    prefix abc;
    namespace "urn:cesnet:mod3";

    typedef my {
        type union {
            type uint8;
            type string;
            type leafref {          // not allow leafref in union
                path "../top";
            }
        }
    }

    leaf l {
        type my;
    }

    leaf top {
        type boolean;
    }
}
