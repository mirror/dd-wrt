module mod5 {
    prefix abc;
    namespace "urn:cesnet:mod5";

    typedef my {
        type leafref {
            path "../../../presence/test";
        }
    }

    container cont {
        list list {
            key keys;

            leaf keys { type string;}

            leaf ref {
                type my;
            }

            leaf ref1 {
                type leafref {
                    path "../../../presence/test";
                }
            }
        }
    }

    container presence {
        leaf test {
            config false;   // must be config true in this case
            type int16;
        }
    }
}
