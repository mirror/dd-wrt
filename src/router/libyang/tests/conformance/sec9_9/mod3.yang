module mod3 {
    prefix abc;
    namespace "urn:cesnet:mod3";

    container cont {
        leaf test {
            type my;
        }
    }

    leaf top {
        type leafref {
            path "../c";
        }
    }

    leaf c {
        type leafref {
            path "../cont/test";   // circular chain of leafrefs
        }
    }

    typedef my {
        type leafref {
            path "../../top";
        }
    }
}
