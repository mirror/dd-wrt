module mod10 {
    prefix abc;
    namespace "urn:cesnet:mod10";

    typedef my {
        type leafref {
            path "../../../presence/test";
        }
    }

    feature f1;

    container cont {
        list list {
            key keys;

            leaf keys { type string;}

            leaf ref {
                type my;
                if-feature f1;
                if-feature f2;
            }

            leaf ref1 {
                type leafref {
                    path "../../../presence/test1";
                }   // missing if-feature f1
            }
        }
    }

    container presence {
        leaf test {
            if-feature f1;
            if-feature f2;
            type int16;
        }

        leaf test1 {
            if-feature f1;
            type boolean;
        }
    }

    feature f2;
}
