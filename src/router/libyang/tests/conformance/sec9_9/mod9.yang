module mod9 {
    prefix abc;
    namespace "urn:cesnet:mod9";

    grouping g {
        leaf target1 {
            type string;
        }

        container cont {
            leaf target2 {
                type uint8;
            }
        }

        container presence {
            presence "enable";

            leaf ref1 {
                type leafref {
                    path ../../cont/target2;
                }
            }

            leaf ref2 {
                type leafref {
                    path "../../../top";
                }
            }
        }
    }

    container ccc {
        uses g;
    }

    leaf top {
        type int32;
    }

    container bb {
        leaf ref {
            type leafref {
                path ../../ccc/target1;
            }
        }
    }
}
