module mod6 {
    prefix abc;
    namespace "urn:cesnet:mod6";

    typedef my {
        type leafref {
            path "../../../presence/test";
        }
    }

    container cont {
        list list {
            key keys;

            leaf keys { type string;}

            leaf ref {
                type my;
            }

            leaf ref1 {
                type leafref {
                    path "../../../presence/test1";  // not found
                }
            }
        }
    }

    container presence {
        presence "enable";
        leaf test {
            type int16;
        }
    }
}
