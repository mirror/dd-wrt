module mod2 {

    prefix abc;
    namespace "urn:cesnet:mod2";

    typedef my {
        type string {
            length "1..245";
            pattern '[a-zA-Z]+';
        }

        default "default";
    }

    container cont {
        leaf-list l1 {
            type my;

            units "names";

            ordered-by system;
        }
    }

    container presence {
        presence "enable";

        leaf-list l2 {
            type my;

            ordered-by user;
        }
    }

    choice ch1 {
        default l4;

        case abc {
            leaf-list l3 {
                type my;

                ordered-by "system";
            }

            container ccc {
                leaf leaf {
                    type string;
                }
            }
        }

        leaf-list l4 {
            type my;

            ordered-by "user";
        }
    }

    container cont1 {
        leaf-list l5 {
            type my;
        }
    }

    container state {
        config false;

        leaf-list l6 {
            type my;

            ordered-by user;
        }
    }
}
