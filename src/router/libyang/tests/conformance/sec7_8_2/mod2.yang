module mod2 {
    prefix abc;
    namespace "urn:cesnet:mod2";

    container ccc {
        list ll1 {
            description "test";
            reference "test";
            status current;

            key k;

            leaf key {
                type string;
            }

            when "../key";
        }

        leaf key {
            type boolean;
        }
    }
}
