module mod3 {
    prefix abc;
    namespace "urn:cesnet:mod3";

    container ccc {
        list ll1 {
            description "test";
            reference "test";
            status current;

            leaf k {
                type int8;
            }

            key "keys k keys"; // repeated key

            leaf keys {
                type string;
            }



            when "../key";
        }

        leaf key {
            type boolean;
        }
    }
}
