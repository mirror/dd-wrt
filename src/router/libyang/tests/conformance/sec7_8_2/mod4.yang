module mod4 {
    prefix bb4;
    namespace "urn:cesnet:mod4";

    typedef my {
        type empty;

        description "test";
    }

    list l1 {
        key "empty";

        container ccc {
            leaf mandatory {
                type int8;
                mandatory true;
            }

            presence "enabled";
        }

        leaf empty { type my; }
    }
}
