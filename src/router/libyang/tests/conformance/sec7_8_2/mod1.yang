module mod1 {
    prefix abc;
    namespace "urn:cesnet:mod1";

    container ccc {
        list ll1 {
            description "test";
            reference "test";
            status current;

            // missing key

            leaf key {
                type string;
            }
        }
    }
}
