module mod6 {
    prefix abc;
    namespace "urn:cesnet:mod6";

    list ll {
        key "config normal state";

        leaf config {
            type string;
            config true;
        }

        leaf normal {
            type string;
        }

        leaf state {
            type string;
            config false;
        }

        container ccc {
            presence "enable";
        }
    }
}
