module mod11 {

    prefix abc;
    namespace "urn:cesnet:mod11";

    leaf-list ll1 {
        type int16;
        description "test description";

        reference "test reference";
        type uint8;
    }
}
