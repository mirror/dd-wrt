module mod5 {

    prefix abc;
    namespace "urn:cesnet:mod5";

    leaf-list ll1 {
            description "test description";

            reference "test reference";

            type string;

            config false;

            status current;

            units "kilogram";
    }

    container ccc {

        leaf-list ll1 {
            config true;

            status "current";

            units counter;

            description "test description";

            reference "test reference";

            type string;

            units obselete; //duplicated
        }
    }
}
