module mod6 {

    prefix abc;
    namespace "urn:cesnet:mod6";

    leaf-list ll1 {
            description "test description";

            reference "test reference";

            type string;

            config false;

            status current;

            units "kilogram";

            when "../user = 'admin' and /password";
    }

    container ccc {

        leaf-list ll1 {
            config true;

            status "current";

            units counter;

            when "../../user = 'admin' and /password";

            description "test description";

            reference "test reference";

            type string;

            when "../../user = 'admin' and /password"; //duplicated
        }
    }

    leaf user {
        type string;
        default "admin";
    }

    leaf password {
        type string;
        default "password";
    }
}
