module mod4 {

    prefix abc;
    namespace "urn:cesnet:mod4";

    leaf-list ll1 {
            description "test description";

            reference "test reference";

            type string;

            config false;

            status current;
    }

    container ccc {

        leaf-list ll1 {
            config true;

            status "current";

            description "test description";

            reference "test reference";

            type string;

            status obsolete; //duplicated
        }
    }
}
