module mod7 {

    prefix abc;
    namespace "urn:cesnet:mod7";

    leaf-list ll1 {
            description "test description";

            reference "test reference";

            type string;

            config false;

            status current;

            units "kilogram";

            when "../user = 'admin' and /password";

            ordered-by system;
    }

    container ccc {

        leaf-list ll1 {
            config true;

            status "current";

            ordered-by "system";

            units counter;

            when "../../user = 'admin' and /password";

            description "test description";

            reference "test reference";

            type string;

            ordered-by user; //duplicated
        }
    }

    leaf user {
        type string;
        default "admin";
    }

    leaf password {
        type string;
        default "password";
    }
}
