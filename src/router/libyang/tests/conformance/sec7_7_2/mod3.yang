module mod3 {

    prefix abc;
    namespace "urn:cesnet:mod3";

    leaf-list ll1 {
            description "test description";

            reference "test reference";

            type string;

            config false;
    }

    container ccc {

        leaf-list ll1 {
            config true;

            description "test description";

            reference "test reference";

            type string;

            config "false"; //duplicated
        }
    }
}
