module mod10 {

    prefix abc;
    namespace "urn:cesnet:mod10";

    leaf-list ll1 {
            description "test description";

            reference "test reference";

            type string;

            config false;

            status current;

            units "kilogram";

            when "../user = 'admin' and /password";

            ordered-by system;

            max-elements "5";

            min-elements 0;
    }

    container ccc {

        leaf-list ll1 {
            config true;

            status "current";

            ordered-by "system";

            max-elements 10;

            min-elements 3;

            units counter;

            when "../../user = 'admin' and /password";

            description "test description";

            reference "test reference";

            // missing type statement

        }
    }

    leaf user {
        type string;
        default "admin";
    }

    leaf password {
        type string;
        default "password";
    }
}
