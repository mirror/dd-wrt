module mod8 {

    prefix abc;
    namespace "urn:cesnet:mod8";

    leaf-list ll1 {
            description "test description";

            reference "test reference";

            type string;

            config false;

            status current;

            units "kilogram";

            when "../user = 'admin' and /password";

            ordered-by system;

            max-elements "5";
    }

    container ccc {

        leaf-list ll1 {
            config true;

            status "current";

            ordered-by "system";

            max-elements 10;

            units counter;

            when "../../user = 'admin' and /password";

            description "test description";

            reference "test reference";

            type string;

            max-elements unbounded; //duplicated
        }
    }

    leaf user {
        type string;
        default "admin";
    }

    leaf password {
        type string;
        default "password";
    }
}
