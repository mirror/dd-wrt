module sm-modp {
  yang-version 1.1;
  namespace "urn:sm-modp";
  prefix "sm-modp";

  import ietf-yang-schema-mount {
    prefix yangmnt;
  }

  revision 2017-01-26;

  container ncmp {
    yangmnt:mount-point "root";
  }

  container not-compiled {
    leaf first {
      type string;
    }
    leaf second {
      type string;
    }
  }
}
